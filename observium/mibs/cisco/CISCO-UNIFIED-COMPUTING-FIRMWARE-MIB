-- *********************************************************************
-- CISCO-UNIFIED-COMPUTING-FIRMWARE-MIB.my
-- 
-- MIB representation of the Cisco Unified Computing System
-- FIRMWARE management information model package
-- 
-- Created June 2015 by Charles Bullis
-- 
-- Copyright (c) 2005-2015 Cisco Systems, Inc. All rights reserved.
-- 
-- *********************************************************************

CISCO-UNIFIED-COMPUTING-FIRMWARE-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsConditionRemoteInvRslt,
    CucsExtpolConnProtocol,
    CucsFirmwareActivityServersPowerState,
    CucsFirmwareActivityUpgradePriorityInfo,
    CucsFirmwareAdminState,
    CucsFirmwareAutoSyncConfigIssue,
    CucsFirmwareAutoSyncState,
    CucsFirmwareBootUnitImage,
    CucsFirmwareCatalogPackConfigState,
    CucsFirmwareCompleteness,
    CucsFirmwareComponentType,
    CucsFirmwareDependencyRelationship,
    CucsFirmwareDependencyScope,
    CucsFirmwareDependencySensitivity,
    CucsFirmwareDistributableFsmCurrentFsm,
    CucsFirmwareDistributableFsmStageName,
    CucsFirmwareDistributableFsmTaskItem,
    CucsFirmwareDistributableType,
    CucsFirmwareDownloadActivity,
    CucsFirmwareDownloaderFsmCurrentFsm,
    CucsFirmwareDownloaderFsmStageName,
    CucsFirmwareDownloaderFsmTaskItem,
    CucsFirmwareEquipmentType,
    CucsFirmwareFirmwareState,
    CucsFirmwareFwState,
    CucsFirmwareHostPackConfigQualifier,
    CucsFirmwareImageDeleted,
    CucsFirmwareImageError,
    CucsFirmwareImageFsmCurrentFsm,
    CucsFirmwareImageFsmStageName,
    CucsFirmwareImageFsmTaskItem,
    CucsFirmwareImagePresence,
    CucsFirmwareImageState,
    CucsFirmwareImpactType,
    CucsFirmwareInstallState,
    CucsFirmwareItemType,
    CucsFirmwarePackItemPresence,
    CucsFirmwarePackMode,
    CucsFirmwareRunningDeployment,
    CucsFirmwareSystemFsmCurrentFsm,
    CucsFirmwareSystemFsmStageName,
    CucsFirmwareSystemFsmTaskFlags,
    CucsFirmwareSystemFsmTaskItem,
    CucsFirmwareTransferState,
    CucsFirmwareTransport,
    CucsFirmwareTriggerState,
    CucsFirmwareType,
    CucsFirmwareUpdatableDeployment,
    CucsFirmwareUpgradeCategory,
    CucsFirmwareUpgradeSeverity,
    CucsFirmwareUpgradeStatus,
    CucsFsmCompletion,
    CucsFsmFlags,
    CucsFsmFsmStageStatus,
    CucsPolicyPolicyOwner,
    CucsTrigAckChangeDetails,
    CucsTrigAckChanges,
    CucsTrigAckDisr,
    CucsTrigAckOperState,
    CucsTrigAckPrevOperState,
    CucsTrigAdminState,
    CucsTrigTrigOperState
        FROM CISCO-UNIFIED-COMPUTING-TC-MIB;

cucsFirmwareObjects MODULE-IDENTITY
    LAST-UPDATED    "201506290000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        FIRMWARE management information model package"
    ::= { ciscoUnifiedComputingMIBObjects 22 }

cucsFirmwareAckTable OBJECT-TYPE
    SYNTAX           SEQUENCE OF CucsFirmwareAckEntry
    MAX-ACCESS       not-accessible
    STATUS           current
    DESCRIPTION
        "Cisco UCS firmware:Ack managed object table"
    ::= { cucsFirmwareObjects 25 }

cucsFirmwareAckEntry OBJECT-TYPE
    SYNTAX           CucsFirmwareAckEntry
    MAX-ACCESS       not-accessible
    STATUS           current
    DESCRIPTION
        "Entry for the cucsFirmwareAckTable table."
    INDEX { cucsFirmwareAckInstanceId }
    ::= { cucsFirmwareAckTable 1 }

CucsFirmwareAckEntry ::= SEQUENCE {
    cucsFirmwareAckInstanceId                                        CucsManagedObjectId,
    cucsFirmwareAckDn                                                CucsManagedObjectDn,
    cucsFirmwareAckRn                                                SnmpAdminString,
    cucsFirmwareAckAcked                                             DateAndTime,
    cucsFirmwareAckAckedBy                                           SnmpAdminString,
    cucsFirmwareAckAdminState                                        CucsTrigAdminState,
    cucsFirmwareAckAutoDelete                                        TruthValue,
    cucsFirmwareAckChangeBy                                          SnmpAdminString,
    cucsFirmwareAckChangeDetails                                     CucsTrigAckChangeDetails,
    cucsFirmwareAckChanges                                           CucsTrigAckChanges,
    cucsFirmwareAckDescr                                             SnmpAdminString,
    cucsFirmwareAckDisr                                              CucsTrigAckDisr,
    cucsFirmwareAckIgnoreCap                                         TruthValue,
    cucsFirmwareAckIntId                                             SnmpAdminString,
    cucsFirmwareAckModified                                          DateAndTime,
    cucsFirmwareAckName                                              SnmpAdminString,
    cucsFirmwareAckOperScheduler                                     SnmpAdminString,
    cucsFirmwareAckOperState                                         CucsTrigAckOperState,
    cucsFirmwareAckPolicyLevel                                       Gauge32,
    cucsFirmwareAckPolicyOwner                                       CucsPolicyPolicyOwner,
    cucsFirmwareAckPrevOperState                                     CucsTrigAckPrevOperState,
    cucsFirmwareAckScheduler                                         SnmpAdminString
}

cucsFirmwareAckInstanceId OBJECT-TYPE
    SYNTAX       CucsManagedObjectId
    MAX-ACCESS   not-accessible
    STATUS       current
    DESCRIPTION
        "Instance identifier of the managed object."
    ::= { cucsFirmwareAckEntry 1 }

cucsFirmwareAckDn OBJECT-TYPE
    SYNTAX       CucsManagedObjectDn
    MAX-ACCESS   read-only
    STATUS       current
    DESCRIPTION
        "Cisco UCS firmware:Ack:dn managed object property"
    ::= { cucsFirmwareAckEntry 2 }

cucsFirmwareAckRn OBJECT-TYPE
    SYNTAX       SnmpAdminString
    MAX-ACCESS   read-only
    STATUS       current
    DESCRIPTION
        "Cisco UCS firmware:Ack:rn managed object property"
    ::= { cucsFirmwareAckEntry 3 }

cucsFirmwareAckAcked OBJECT-TYPE
    SYNTAX       DateAndTime
    MAX-ACCESS   read-only
    STATUS       current
    DESCRIPTION
        "Cisco UCS firmware:Ack:acked managed object property"
    ::= { cucsFirmwareAckEntry 4 }

cucsFirmwareAckAckedBy OBJECT-TYPE
    SYNTAX       SnmpAdminString
    MAX-ACCESS   read-only
    STATUS       current
    DESCRIPTION
        "Cisco UCS firmware:Ack:ackedBy managed object property"
    ::= { cucsFirmwareAckEntry 5 }

cucsFirmwareAckAdminState OBJECT-TYPE
    SYNTAX       CucsTrigAdminState
    MAX-ACCESS   read-only
    STATUS       current
    DESCRIPTION
        "Cisco UCS firmware:Ack:adminState managed object property"
    ::= { cucsFirmwareAckEntry 6 }

cucsFirmwareAckAutoDelete OBJECT-TYPE
    SYNTAX       TruthValue
    MAX-ACCESS   read-only
    STATUS       current
    DESCRIPTION
        "Cisco UCS firmware:Ack:autoDelete managed object property"
    ::= { cucsFirmwareAckEntry 7 }

cucsFirmwareAckChangeBy OBJECT-TYPE
    SYNTAX       SnmpAdminString
    MAX-ACCESS   read-only
    STATUS       current
    DESCRIPTION
        "Cisco UCS firmware:Ack:changeBy managed object property"
    ::= { cucsFirmwareAckEntry 8 }

cucsFirmwareAckChangeDetails OBJECT-TYPE
    SYNTAX       CucsTrigAckChangeDetails
    MAX-ACCESS   read-only
    STATUS       current
    DESCRIPTION
        "Cisco UCS firmware:Ack:changeDetails managed object property"
    ::= { cucsFirmwareAckEntry 9 }

cucsFirmwareAckChanges OBJECT-TYPE
    SYNTAX       CucsTrigAckChanges
    MAX-ACCESS   read-only
    STATUS       current
    DESCRIPTION
        "Cisco UCS firmware:Ack:changes managed object property"
    ::= { cucsFirmwareAckEntry 10 }

cucsFirmwareAckDescr OBJECT-TYPE
    SYNTAX       SnmpAdminString
    MAX-ACCESS   read-only
    STATUS       current
    DESCRIPTION
        "Cisco UCS firmware:Ack:descr managed object property"
    ::= { cucsFirmwareAckEntry 11 }

cucsFirmwareAckDisr OBJECT-TYPE
    SYNTAX       CucsTrigAckDisr
    MAX-ACCESS   read-only
    STATUS       current
    DESCRIPTION
        "Cisco UCS firmware:Ack:disr managed object property"
    ::= { cucsFirmwareAckEntry 12 }

cucsFirmwareAckIgnoreCap OBJECT-TYPE
    SYNTAX       TruthValue
    MAX-ACCESS   read-only
    STATUS       current
    DESCRIPTION
        "Cisco UCS firmware:Ack:ignoreCap managed object property"
    ::= { cucsFirmwareAckEntry 13 }

cucsFirmwareAckIntId OBJECT-TYPE
    SYNTAX       SnmpAdminString
    MAX-ACCESS   read-only
    STATUS       current
    DESCRIPTION
        "Cisco UCS firmware:Ack:intId managed object property"
    ::= { cucsFirmwareAckEntry 14 }

cucsFirmwareAckModified OBJECT-TYPE
    SYNTAX       DateAndTime
    MAX-ACCESS   read-only
    STATUS       current
    DESCRIPTION
        "Cisco UCS firmware:Ack:modified managed object property"
    ::= { cucsFirmwareAckEntry 15 }

cucsFirmwareAckName OBJECT-TYPE
    SYNTAX       SnmpAdminString
    MAX-ACCESS   read-only
    STATUS       current
    DESCRIPTION
        "Cisco UCS firmware:Ack:name managed object property"
    ::= { cucsFirmwareAckEntry 16 }

cucsFirmwareAckOperScheduler OBJECT-TYPE
    SYNTAX       SnmpAdminString
    MAX-ACCESS   read-only
    STATUS       current
    DESCRIPTION
        "Cisco UCS firmware:Ack:operScheduler managed object property"
    ::= { cucsFirmwareAckEntry 17 }

cucsFirmwareAckOperState OBJECT-TYPE
    SYNTAX       CucsTrigAckOperState
    MAX-ACCESS   read-only
    STATUS       current
    DESCRIPTION
        "Cisco UCS firmware:Ack:operState managed object property"
    ::= { cucsFirmwareAckEntry 18 }

cucsFirmwareAckPolicyLevel OBJECT-TYPE
    SYNTAX       Gauge32
    MAX-ACCESS   read-only
    STATUS       current
    DESCRIPTION
        "Cisco UCS firmware:Ack:policyLevel managed object property"
    ::= { cucsFirmwareAckEntry 19 }

cucsFirmwareAckPolicyOwner OBJECT-TYPE
    SYNTAX       CucsPolicyPolicyOwner
    MAX-ACCESS   read-only
    STATUS       current
    DESCRIPTION
        "Cisco UCS firmware:Ack:policyOwner managed object property"
    ::= { cucsFirmwareAckEntry 20 }

cucsFirmwareAckPrevOperState OBJECT-TYPE
    SYNTAX       CucsTrigAckPrevOperState
    MAX-ACCESS   read-only
    STATUS       current
    DESCRIPTION
        "Cisco UCS firmware:Ack:prevOperState managed object property"
    ::= { cucsFirmwareAckEntry 21 }

cucsFirmwareAckScheduler OBJECT-TYPE
    SYNTAX       SnmpAdminString
    MAX-ACCESS   read-only
    STATUS       current
    DESCRIPTION
        "Cisco UCS firmware:Ack:scheduler managed object property"
    ::= { cucsFirmwareAckEntry 22 }

cucsFirmwareActivityTable OBJECT-TYPE
    SYNTAX           SEQUENCE OF CucsFirmwareActivityEntry
    MAX-ACCESS       not-accessible
    STATUS           current
    DESCRIPTION
        "Cisco UCS firmware:Activity managed object table"
    ::= { cucsFirmwareObjects 59 }

cucsFirmwareActivityEntry OBJECT-TYPE
    SYNTAX           CucsFirmwareActivityEntry
    MAX-ACCESS       not-accessible
    STATUS           current
    DESCRIPTION
        "Entry for the cucsFirmwareActivityTable table."
    INDEX { cucsFirmwareActivityInstanceId }
    ::= { cucsFirmwareActivityTable 1 }

CucsFirmwareActivityEntry ::= SEQUENCE {
    cucsFirmwareActivityInstanceId                                   CucsManagedObjectId,
    cucsFirmwareActivityDn                                           CucsManagedObjectDn,
    cucsFirmwareActivityRn                                           SnmpAdminString,
    cucsFirmwareActivityChassisCompInActivationDn                    SnmpAdminString,
    cucsFirmwareActivityServerCompInActivationDn                     SnmpAdminString,
    cucsFirmwareActivityServersPowerState                            CucsFirmwareActivityServersPowerState,
    cucsFirmwareActivityUpgradePriorityInfo                          CucsFirmwareActivityUpgradePriorityInfo
}

cucsFirmwareActivityInstanceId OBJECT-TYPE
    SYNTAX       CucsManagedObjectId
    MAX-ACCESS   not-accessible
    STATUS       current
    DESCRIPTION
        "Instance identifier of the managed object."
    ::= { cucsFirmwareActivityEntry 1 }

cucsFirmwareActivityDn OBJECT-TYPE
    SYNTAX       CucsManagedObjectDn
    MAX-ACCESS   read-only
    STATUS       current
    DESCRIPTION
        "Cisco UCS firmware:Activity:dn managed object property"
    ::= { cucsFirmwareActivityEntry 2 }

cucsFirmwareActivityRn OBJECT-TYPE
    SYNTAX       SnmpAdminString
    MAX-ACCESS   read-only
    STATUS       current
    DESCRIPTION
        "Cisco UCS firmware:Activity:rn managed object property"
    ::= { cucsFirmwareActivityEntry 3 }

cucsFirmwareActivityChassisCompInActivationDn OBJECT-TYPE
    SYNTAX       SnmpAdminString
    MAX-ACCESS   read-only
    STATUS       current
    DESCRIPTION
        "Cisco UCS firmware:Activity:chassisCompInActivationDn
        managed object property"
    ::= { cucsFirmwareActivityEntry 4 }

cucsFirmwareActivityServerCompInActivationDn OBJECT-TYPE
    SYNTAX       SnmpAdminString
    MAX-ACCESS   read-only
    STATUS       current
    DESCRIPTION
        "Cisco UCS firmware:Activity:serverCompInActivationDn
        managed object property"
    ::= { cucsFirmwareActivityEntry 5 }

cucsFirmwareActivityServersPowerState OBJECT-TYPE
    SYNTAX       CucsFirmwareActivityServersPowerState
    MAX-ACCESS   read-only
    STATUS       current
    DESCRIPTION
        "Cisco UCS firmware:Activity:serversPowerState
        managed object property"
    ::= { cucsFirmwareActivityEntry 6 }

cucsFirmwareActivityUpgradePriorityInfo OBJECT-TYPE
    SYNTAX       CucsFirmwareActivityUpgradePriorityInfo
    MAX-ACCESS   read-only
    STATUS       current
    DESCRIPTION
        "Cisco UCS firmware:Activity:upgradePriorityInfo
        managed object property"
    ::= { cucsFirmwareActivityEntry 7 }

cucsFirmwareAutoSyncPolicyTable OBJECT-TYPE
    SYNTAX           SEQUENCE OF CucsFirmwareAutoSyncPolicyEntry
    MAX-ACCESS       not-accessible
    STATUS           current
    DESCRIPTION
        "Cisco UCS firmware:AutoSyncPolicy managed object table"
    ::= { cucsFirmwareObjects 50 }

cucsFirmwareAutoSyncPolicyEntry OBJECT-TYPE
    SYNTAX           CucsFirmwareAutoSyncPolicyEntry
    MAX-ACCESS       not-accessible
    STATUS           current
    DESCRIPTION
        "Entry for the cucsFirmwareAutoSyncPolicyTable table."
    INDEX { cucsFirmwareAutoSyncPolicyInstanceId }
    ::= { cucsFirmwareAutoSyncPolicyTable 1 }

CucsFirmwareAutoSyncPolicyEntry ::= SEQUENCE {
    cucsFirmwareAutoSyncPolicyInstanceId                             CucsManagedObjectId,
    cucsFirmwareAutoSyncPolicyDn                                     CucsManagedObjectDn,
    cucsFirmwareAutoSyncPolicyRn                                     SnmpAdminString,
    cucsFirmwareAutoSyncPolicyConfigIssue                            CucsFirmwareAutoSyncConfigIssue,
    cucsFirmwareAutoSyncPolicyDescr                                  SnmpAdminString,
    cucsFirmwareAutoSyncPolicyIntId                                  SnmpAdminString,
    cucsFirmwareAutoSyncPolicyName                                   SnmpAdminString,
    cucsFirmwareAutoSyncPolicyPolicyLevel                            Gauge32,
    cucsFirmwareAutoSyncPolicyPolicyOwner                            CucsPolicyPolicyOwner,
    cucsFirmwareAutoSyncPolicySyncState                              CucsFirmwareAutoSyncState
}

cucsFirmwareAutoSyncPolicyInstanceId OBJECT-TYPE
    SYNTAX       CucsManagedObjectId
    MAX-ACCESS   not-accessible
    STATUS       current
    DESCRIPTION
        "Instance identifier of the managed object."
    ::= { cucsFirmwareAutoSyncPolicyEntry 1 }

cucsFirmwareAutoSyncPolicyDn OBJECT-TYPE
    SYNTAX       CucsManagedObjectDn
    MAX-ACCESS   read-only
    STATUS       current
    DESCRIPTION
        "Cisco UCS firmware:AutoSyncPolicy:dn managed object property"
    ::= { cucsFirmwareAutoSyncPolicyEntry 2 }

cucsFirmwareAutoSyncPolicyRn OBJECT-TYPE
    SYNTAX       SnmpAdminString
    MAX-ACCESS   read-only
    STATUS       current
    DESCRIPTION
        "Cisco UCS firmware:AutoSyncPolicy:rn managed object property"
    ::= { cucsFirmwareAutoSyncPolicyEntry 3 }

cucsFirmwareAutoSyncPolicyConfigIssue OBJECT-TYPE
    SYNTAX       CucsFirmwareAutoSyncConfigIssue
    MAX-ACCESS   read-only
    STATUS       current
    DESCRIPTION
        "Cisco UCS firmware:AutoSyncPolicy:configIssue
        managed object property"
    ::= { cucsFirmwareAutoSyncPolicyEntry 4 }

cucsFirmwareAutoSyncPolicyDescr OBJECT-TYPE
    SYNTAX       SnmpAdminString
    MAX-ACCESS   read-only
    STATUS       current
    DESCRIPTION
        "Cisco UCS firmware:AutoSyncPolicy:descr managed object property"
    ::= { cucsFirmwareAutoSyncPolicyEntry 5 }

cucsFirmwareAutoSyncPolicyIntId OBJECT-TYPE
    SYNTAX       SnmpAdminString
    MAX-ACCESS   read-only
    STATUS       current
    DESCRIPTION
        "Cisco UCS firmware:AutoSyncPolicy:intId managed object property"
    ::= { cucsFirmwareAutoSyncPolicyEntry 6 }

cucsFirmwareAutoSyncPolicyName OBJECT-TYPE
    SYNTAX       SnmpAdminString
    MAX-ACCESS   read-only
    STATUS       current
    DESCRIPTION
        "Cisco UCS firmware:AutoSyncPolicy:name managed object property"
    ::= { cucsFirmwareAutoSyncPolicyEntry 7 }

cucsFirmwareAutoSyncPolicyPolicyLevel OBJECT-TYPE
    SYNTAX       Gauge32
    MAX-ACCESS   read-only
    STATUS       current
    DESCRIPTION
        "Cisco UCS firmware:AutoSyncPolicy:policyLevel
        managed object property"
    ::= { cucsFirmwareAutoSyncPolicyEntry 8 }

cucsFirmwareAutoSyncPolicyPolicyOwner OBJECT-TYPE
    SYNTAX       CucsPolicyPolicyOwner
    MAX-ACCESS   read-only
    STATUS       current
    DESCRIPTION
        "Cisco UCS firmware:AutoSyncPolicy:policyOwner
        managed object property"
    ::= { cucsFirmwareAutoSyncPolicyEntry 9 }

cucsFirmwareAutoSyncPolicySyncState OBJECT-TYPE
    SYNTAX       CucsFirmwareAutoSyncState
    MAX-ACCESS   read-only
    STATUS       current
    DESCRIPTION
        "Cisco UCS firmware:AutoSyncPolicy:syncState managed
        object property"
    ::= { cucsFirmwareAutoSyncPolicyEntry 10 }

cucsFirmwareBladeTable OBJECT-TYPE
    SYNTAX           SEQUENCE OF CucsFirmwareBladeEntry
    MAX-ACCESS       not-accessible
    STATUS           current
    DESCRIPTION
        "Cisco UCS firmware:Blade managed object table"
    ::= { cucsFirmwareObjects 26 }

cucsFirmwareBladeEntry OBJECT-TYPE
    SYNTAX           CucsFirmwareBladeEntry
    MAX-ACCESS       not-accessible
    STATUS           current
    DESCRIPTION
        "Entry for the cucsFirmwareBladeTable table."
    INDEX { cucsFirmwareBladeInstanceId }
    ::= { cucsFirmwareBladeTable 1 }

CucsFirmwareBladeEntry ::= SEQUENCE {
    cucsFirmwareBladeInstanceId                                      CucsManagedObjectId,
    cucsFirmwareBladeDn                                              CucsManagedObjectDn,
    cucsFirmwareBladeRn                                              SnmpAdminString,
    cucsFirmwareBladeOperVersion                                     SnmpAdminString
}

cucsFirmwareBladeInstanceId OBJECT-TYPE
    SYNTAX       CucsManagedObjectId
    MAX-ACCESS   not-accessible
    STATUS       current
    DESCRIPTION
        "Instance identifier of the managed object."
    ::= { cucsFirmwareBladeEntry 1 }

cucsFirmwareBladeDn OBJECT-TYPE
    SYNTAX       CucsManagedObjectDn
    MAX-ACCESS   read-only
    STATUS       current
    DESCRIPTION
        "Cisco UCS firmware:Blade:dn managed object property"
    ::= { cucsFirmwareBladeEntry 2 }

cucsFirmwareBladeRn OBJECT-TYPE
    SYNTAX       SnmpAdminString
    MAX-ACCESS   read-only
    STATUS       current
    DESCRIPTION
        "Cisco UCS firmware:Blade:rn managed object property"
    ::= { cucsFirmwareBladeEntry 3 }

cucsFirmwareBladeOperVersion OBJECT-TYPE
    SYNTAX       SnmpAdminString
    MAX-ACCESS   read-only
    STATUS       current
    DESCRIPTION
        "Cisco UCS firmware:Blade:operVersion managed object property"
    ::= { cucsFirmwareBladeEntry 4 }

cucsFirmwareBootDefinitionTable OBJECT-TYPE
    SYNTAX           SEQUENCE OF CucsFirmwareBootDefinitionEntry
    MAX-ACCESS       not-accessible
    STATUS           current
    DESCRIPTION
        "Cisco UCS firmware:BootDefinition managed object table"
    ::= { cucsFirmwareObjects 1 }

cucsFirmwareBootDefinitionEntry OBJECT-TYPE
    SYNTAX           CucsFirmwareBootDefinitionEntry
    MAX-ACCESS       not-accessible
    STATUS           current
    DESCRIPTION
        "Entry for the cucsFirmwareBootDefinitionTable table."
    INDEX { cucsFirmwareBootDefinitionInstanceId }
    ::= { cucsFirmwareBootDefinitionTable 1 }

CucsFirmwareBootDefinitionEntry ::= SEQUENCE {
    cucsFirmwareBootDefinitionInstanceId                             CucsManagedObjectId,
    cucsFirmwareBootDefinitionDn                                     CucsManagedObjectDn,
    cucsFirmwareBootDefinitionRn                                     SnmpAdminString,
    cucsFirmwareBootDefinitionType                                   CucsFirmwareType
}

cucsFirmwareBootDefinitionInstanceId OBJECT-TYPE
    SYNTAX       CucsManagedObjectId
    MAX-ACCESS   not-accessible
    STATUS       current
    DESCRIPTION
        "Instance identifier of the managed object."
    ::= { cucsFirmwareBootDefinitionEntry 1 }

cucsFirmwareBootDefinitionDn OBJECT-TYPE
    SYNTAX       CucsManagedObjectDn
    MAX-ACCESS   read-only
    STATUS       current
    DESCRIPTION
        "Cisco UCS firmware:BootDefinition:dn managed object property"
    ::= { cucsFirmwareBootDefinitionEntry 2 }

cucsFirmwareBootDefinitionRn OBJECT-TYPE
    SYNTAX       SnmpAdminString
    MAX-ACCESS   read-only
    STATUS       current
    DESCRIPTION
        "Cisco UCS firmware:BootDefinition:rn managed object property"
    ::= { cucsFirmwareBootDefinitionEntry 3 }

cucsFirmwareBootDefinitionType OBJECT-TYPE
    SYNTAX       CucsFirmwareType
    MAX-ACCESS   read-only
    STATUS       current
    DESCRIPTION
        "Cisco UCS firmware:BootDefinition:type managed object property"
    ::= { cucsFirmwareBootDefinitionEntry 4 }

cucsFirmwareBootUnitTable OBJECT-TYPE
    SYNTAX           SEQUENCE OF CucsFirmwareBootUnitEntry
    MAX-ACCESS       not-accessible
    STATUS           current
    DESCRIPTION
        "Cisco UCS firmware:BootUnit managed object table"
    ::= { cucsFirmwareObjects 2 }

cucsFirmwareBootUnitEntry OBJECT-TYPE
    SYNTAX           CucsFirmwareBootUnitEntry
    MAX-ACCESS       not-accessible
    STATUS           current
    DESCRIPTION
        "Entry for the cucsFirmwareBootUnitTable table."
    INDEX { cucsFirmwareBootUnitInstanceId }
    ::= { cucsFirmwareBootUnitTable 1 }

CucsFirmwareBootUnitEntry ::= SEQUENCE {
    cucsFirmwareBootUnitInstanceId                                   CucsManagedObjectId,
    cucsFirmwareBootUnitDn                                           CucsManagedObjectDn,
    cucsFirmwareBootUnitRn                                           SnmpAdminString,
    cucsFirmwareBootUnitAdminState                                   CucsFirmwareTriggerState,
    cucsFirmwareBootUnitIgnoreCompCheck                              TruthValue,
    cucsFirmwareBootUnitImage                                        CucsFirmwareBootUnitImage,
    cucsFirmwareBootUnitOperState                                    CucsFirmwareImageState,
    cucsFirmwareBootUnitPrevVersion                                  SnmpAdminString,
    cucsFirmwareBootUnitResetOnActivate                              TruthValue,
    cucsFirmwareBootUnitType                                         CucsFirmwareComponentType,
    cucsFirmwareBootUnitVersion                                      SnmpAdminString,
    cucsFirmwareBootUnitSkipValidation                               TruthValue
}

cucsFirmwareBootUnitInstanceId OBJECT-TYPE
    SYNTAX       CucsManagedObjectId
    MAX-ACCESS   not-accessible
    STATUS       current
    DESCRIPTION
        "Instance identifier of the managed object."
    ::= { cucsFirmwareBootUnitEntry 1 }

cucsFirmwareBootUnitDn OBJECT-TYPE
    SYNTAX       CucsManagedObjectDn
    MAX-ACCESS   read-only
    STATUS       current
    DESCRIPTION
        "Cisco UCS firmware:BootUnit:dn managed object property"
    ::= { cucsFirmwareBootUnitEntry 2 }

cucsFirmwareBootUnitRn OBJECT-TYPE
    SYNTAX       SnmpAdminString
    MAX-ACCESS   read-only
    STATUS       current
    DESCRIPTION
        "Cisco UCS firmware:BootUnit:rn managed object property"
    ::= { cucsFirmwareBootUnitEntry 3 }

cucsFirmwareBootUnitAdminState OBJECT-TYPE
    SYNTAX       CucsFirmwareTriggerState
    MAX-ACCESS   read-only
    STATUS       current
    DESCRIPTION
        "Cisco UCS firmware:BootUnit:adminState managed object property"
    ::= { cucsFirmwareBootUnitEntry 4 }

cucsFirmwareBootUnitIgnoreCompCheck OBJECT-TYPE
    SYNTAX       TruthValue
    MAX-ACCESS   read-only
    STATUS       current
    DESCRIPTION
        "Cisco UCS firmware:BootUnit:ignoreCompCheck managed
        object property"
    ::= { cucsFirmwareBootUnitEntry 5 }

cucsFirmwareBootUnitImage OBJECT-TYPE
    SYNTAX       CucsFirmwareBootUnitImage
    MAX-ACCESS   read-only
    STATUS       current
    DESCRIPTION
        "Cisco UCS firmware:BootUnit:image managed object property"
    ::= { cucsFirmwareBootUnitEntry 6 }

cucsFirmwareBootUnitOperState OBJECT-TYPE
    SYNTAX       CucsFirmwareImageState
    MAX-ACCESS   read-only
    STATUS       current
    DESCRIPTION
        "Cisco UCS firmware:BootUnit:operState managed object property"
    ::= { cucsFirmwareBootUnitEntry 7 }

cucsFirmwareBootUnitPrevVersion OBJECT-TYPE
    SYNTAX       SnmpAdminString
    MAX-ACCESS   read-only
    STATUS       current
    DESCRIPTION
        "Cisco UCS firmware:BootUnit:prevVersion managed object property"
    ::= { cucsFirmwareBootUnitEntry 8 }

cucsFirmwareBootUnitResetOnActivate OBJECT-TYPE
    SYNTAX       TruthValue
    MAX-ACCESS   read-only
    STATUS       current
    DESCRIPTION
        "Cisco UCS firmware:BootUnit:resetOnActivate managed
        object property"
    ::= { cucsFirmwareBootUnitEntry 9 }

cucsFirmwareBootUnitType OBJECT-TYPE
    SYNTAX       CucsFirmwareComponentType
    MAX-ACCESS   read-only
    STATUS       current
    DESCRIPTION
        "Cisco UCS firmware:BootUnit:type managed object property"
    ::= { cucsFirmwareBootUnitEntry 10 }

cucsFirmwareBootUnitVersion OBJECT-TYPE
    SYNTAX       SnmpAdminString
    MAX-ACCESS   read-only
    STATUS       current
    DESCRIPTION
        "Cisco UCS firmware:BootUnit:version managed object property"
    ::= { cucsFirmwareBootUnitEntry 11 }

cucsFirmwareBootUnitSkipValidation OBJECT-TYPE
    SYNTAX       TruthValue
    MAX-ACCESS   read-only
    STATUS       current
    DESCRIPTION
        "Cisco UCS firmware:BootUnit:skipValidation managed
        object property"
    ::= { cucsFirmwareBootUnitEntry 12 }

cucsFirmwareBundleInfoTable OBJECT-TYPE
    SYNTAX           SEQUENCE OF CucsFirmwareBundleInfoEntry
    MAX-ACCESS       not-accessible
    STATUS           current
    DESCRIPTION
        "Cisco UCS firmware:BundleInfo managed object table"
    ::= { cucsFirmwareObjects 27 }

cucsFirmwareBundleInfoEntry OBJECT-TYPE
    SYNTAX           CucsFirmwareBundleInfoEntry
    MAX-ACCESS       not-accessible
    STATUS           current
    DESCRIPTION
        "Entry for the cucsFirmwareBundleInfoTable table."
    INDEX { cucsFirmwareBundleInfoInstanceId }
    ::= { cucsFirmwareBundleInfoTable 1 }

CucsFirmwareBundleInfoEntry ::= SEQUENCE {
    cucsFirmwareBundleInfoInstanceId                                 CucsManagedObjectId,
    cucsFirmwareBundleInfoDn                                         CucsManagedObjectDn,
    cucsFirmwareBundleInfoRn                                         SnmpAdminString,
    cucsFirmwareBundleInfoType                                       CucsFirmwareDistributableType,
    cucsFirmwareBundleInfoVersion                                    SnmpAdminString
}

cucsFirmwareBundleInfoInstanceId OBJECT-TYPE
    SYNTAX       CucsManagedObjectId
    MAX-ACCESS   not-accessible
    STATUS       current
    DESCRIPTION
        "Instance identifier of the managed object."
    ::= { cucsFirmwareBundleInfoEntry 1 }

cucsFirmwareBundleInfoDn OBJECT-TYPE
    SYNTAX       CucsManagedObjectDn
    MAX-ACCESS   read-only
    STATUS       current
    DESCRIPTION
        "Cisco UCS firmware:BundleInfo:dn managed object property"
    ::= { cucsFirmwareBundleInfoEntry 2 }

cucsFirmwareBundleInfoRn OBJECT-TYPE
    SYNTAX       SnmpAdminString
    MAX-ACCESS   read-only
    STATUS       current
    DESCRIPTION
        "Cisco UCS firmware:BundleInfo:rn managed object property"
    ::= { cucsFirmwareBundleInfoEntry 3 }

cucsFirmwareBundleInfoType OBJECT-TYPE
    SYNTAX       CucsFirmwareDistributableType
    MAX-ACCESS   read-only
    STATUS       current
    DESCRIPTION
        "Cisco UCS firmware:BundleInfo:type managed object property"
    ::= { cucsFirmwareBundleInfoEntry 4 }

cucsFirmwareBundleInfoVersion OBJECT-TYPE
    SYNTAX       SnmpAdminString
    MAX-ACCESS   read-only
    STATUS       current
    DESCRIPTION
        "Cisco UCS firmware:BundleInfo:version managed object property"
    ::= { cucsFirmwareBundleInfoEntry 5 }

cucsFirmwareBundleInfoDigestTable OBJECT-TYPE
    SYNTAX           SEQUENCE OF CucsFirmwareBundleInfoDigestEntry
    MAX-ACCESS       not-accessible
    STATUS           current
    DESCRIPTION
        "Cisco UCS firmware:BundleInfoDigest managed object table"
    ::= { cucsFirmwareObjects 28 }

cucsFirmwareBundleInfoDigestEntry OBJECT-TYPE
    SYNTAX           CucsFirmwareBundleInfoDigestEntry
    MAX-ACCESS       not-accessible
    STATUS           current
    DESCRIPTION
        "Entry for the cucsFirmwareBundleInfoDigestTable table."
    INDEX { cucsFirmwareBundleInfoDigestInstanceId }
    ::= { cucsFirmwareBundleInfoDigestTable 1 }

CucsFirmwareBundleInfoDigestEntry ::= SEQUENCE {
    cucsFirmwareBundleInfoDigestInstanceId                           CucsManagedObjectId,
    cucsFirmwareBundleInfoDigestDn                                   CucsManagedObjectDn,
    cucsFirmwareBundleInfoDigestRn                                   SnmpAdminString,
    cucsFirmwareBundleInfoDigestBundleName                           SnmpAdminString,
    cucsFirmwareBundleInfoDigestType                                 CucsFirmwareDistributableType,
    cucsFirmwareBundleInfoDigestVersion                              SnmpAdminString
}

cucsFirmwareBundleInfoDigestInstanceId OBJECT-TYPE
    SYNTAX       CucsManagedObjectId
    MAX-ACCESS   not-accessible
    STATUS       current
    DESCRIPTION
        "Instance identifier of the managed object."
    ::= { cucsFirmwareBundleInfoDigestEntry 1 }

cucsFirmwareBundleInfoDigestDn OBJECT-TYPE
    SYNTAX       CucsManagedObjectDn
    MAX-ACCESS   read-only
    STATUS       current
    DESCRIPTION
        "Cisco UCS firmware:BundleInfoDigest:dn managed object property"
    ::= { cucsFirmwareBundleInfoDigestEntry 2 }

cucsFirmwareBundleInfoDigestRn OBJECT-TYPE
    SYNTAX       SnmpAdminString
    MAX-ACCESS   read-only
    STATUS       current
    DESCRIPTION
        "Cisco UCS firmware:BundleInfoDigest:rn managed object property"
    ::= { cucsFirmwareBundleInfoDigestEntry 3 }

cucsFirmwareBundleInfoDigestBundleName OBJECT-TYPE
    SYNTAX       SnmpAdminString
    MAX-ACCESS   read-only
    STATUS       current
    DESCRIPTION
        "Cisco UCS firmware:BundleInfoDigest:bundleName
        managed object property"
    ::= { cucsFirmwareBundleInfoDigestEntry 4 }

cucsFirmwareBundleInfoDigestType OBJECT-TYPE
    SYNTAX       CucsFirmwareDistributableType
    MAX-ACCESS   read-only
    STATUS       current
    DESCRIPTION
        "Cisco UCS firmware:BundleInfoDigest:type managed object property"
    ::= { cucsFirmwareBundleInfoDigestEntry 5 }

cucsFirmwareBundleInfoDigestVersion OBJECT-TYPE
    SYNTAX       SnmpAdminString
    MAX-ACCESS   read-only
    STATUS       current
    DESCRIPTION
        "Cisco UCS firmware:BundleInfoDigest:version managed
        object property"
    ::= { cucsFirmwareBundleInfoDigestEntry 6 }

cucsFirmwareBundleTypeTable OBJECT-TYPE
    SYNTAX           SEQUENCE OF CucsFirmwareBundleTypeEntry
    MAX-ACCESS       not-accessible
    STATUS           current
    DESCRIPTION
        "Cisco UCS firmware:BundleType managed object table"
    ::= { cucsFirmwareObjects 21 }

cucsFirmwareBundleTypeEntry OBJECT-TYPE
    SYNTAX           CucsFirmwareBundleTypeEntry
    MAX-ACCESS       not-accessible
    STATUS           current
    DESCRIPTION
        "Entry for the cucsFirmwareBundleTypeTable table."
    INDEX { cucsFirmwareBundleTypeInstanceId }
    ::= { cucsFirmwareBundleTypeTable 1 }

CucsFirmwareBundleTypeEntry ::= SEQUENCE {
    cucsFirmwareBundleTypeInstanceId                                 CucsManagedObjectId,
    cucsFirmwareBundleTypeDn                                         CucsManagedObjectDn,
    cucsFirmwareBundleTypeRn                                         SnmpAdminString,
    cucsFirmwareBundleTypeInvTag                                     SnmpAdminString,
    cucsFirmwareBundleTypeType                                       CucsFirmwareDistributableType
}

cucsFirmwareBundleTypeInstanceId OBJECT-TYPE
    SYNTAX       CucsManagedObjectId
    MAX-ACCESS   not-accessible
    STATUS       current
    DESCRIPTION
        "Instance identifier of the managed object."
    ::= { cucsFirmwareBundleTypeEntry 1 }

cucsFirmwareBundleTypeDn OBJECT-TYPE
    SYNTAX       CucsManagedObjectDn
    MAX-ACCESS   read-only
    STATUS       current
    DESCRIPTION
        "Cisco UCS firmware:BundleType:dn managed object property"
    ::= { cucsFirmwareBundleTypeEntry 2 }

cucsFirmwareBundleTypeRn OBJECT-TYPE
    SYNTAX       SnmpAdminString
    MAX-ACCESS   read-only
    STATUS       current
    DESCRIPTION
        "Cisco UCS firmware:BundleType:rn managed object property"
    ::= { cucsFirmwareBundleTypeEntry 3 }

cucsFirmwareBundleTypeInvTag OBJECT-TYPE
    SYNTAX       SnmpAdminString
    MAX-ACCESS   read-only
    STATUS       current
    DESCRIPTION
        "Cisco UCS firmware:BundleType:invTag managed object property"
    ::= { cucsFirmwareBundleTypeEntry 4 }

cucsFirmwareBundleTypeType OBJECT-TYPE
    SYNTAX       CucsFirmwareDistributableType
    MAX-ACCESS   read-only
    STATUS       current
    DESCRIPTION
        "Cisco UCS firmware:BundleType:type managed object property"
    ::= { cucsFirmwareBundleTypeEntry 5 }

cucsFirmwareBundleTypeCapProviderTable OBJECT-TYPE
    SYNTAX           SEQUENCE OF CucsFirmwareBundleTypeCapProviderEntry
    MAX-ACCESS       not-accessible
    STATUS           current
    DESCRIPTION
        "Cisco UCS firmware:BundleTypeCapProvider managed object table"
    ::= { cucsFirmwareObjects 22 }

cucsFirmwareBundleTypeCapProviderEntry OBJECT-TYPE
    SYNTAX           CucsFirmwareBundleTypeCapProviderEntry
    MAX-ACCESS       not-accessible
    STATUS           current
    DESCRIPTION
        "Entry for the cucsFirmwareBundleTypeCapProviderTable table."
    INDEX { cucsFirmwareBundleTypeCapProviderInstanceId }
    ::= { cucsFirmwareBundleTypeCapProviderTable 1 }

CucsFirmwareBundleTypeCapProviderEntry ::= SEQUENCE {
    cucsFirmwareBundleTypeCapProviderInstanceId                      CucsManagedObjectId,
    cucsFirmwareBundleTypeCapProviderDn                              CucsManagedObjectDn,
    cucsFirmwareBundleTypeCapProviderRn                              SnmpAdminString,
    cucsFirmwareBundleTypeCapProviderDeleted                         TruthValue,
    cucsFirmwareBundleTypeCapProviderDeprecated                      TruthValue,
    cucsFirmwareBundleTypeCapProviderGencount                        Gauge32,
    cucsFirmwareBundleTypeCapProviderMgmtPlaneVer                    SnmpAdminString,
    cucsFirmwareBundleTypeCapProviderModel                           SnmpAdminString,
    cucsFirmwareBundleTypeCapProviderVendor                          SnmpAdminString,
    cucsFirmwareBundleTypeCapProviderElementLoadFailures             Gauge32,
    cucsFirmwareBundleTypeCapProviderElementsLoaded                  Gauge32,
    cucsFirmwareBundleTypeCapProviderLoadErrors                      Gauge32,
    cucsFirmwareBundleTypeCapProviderLoadWarnings                    Gauge32
}

cucsFirmwareBundleTypeCapProviderInstanceId OBJECT-TYPE
    SYNTAX       CucsManagedObjectId
    MAX-ACCESS   not-accessible
    STATUS       current
    DESCRIPTION
        "Instance identifier of the managed object."
    ::= { cucsFirmwareBundleTypeCapProviderEntry 1 }

cucsFirmwareBundleTypeCapProviderDn OBJECT-TYPE
    SYNTAX       CucsManagedObjectDn
    MAX-ACCESS   read-only
    STATUS       current
    DESCRIPTION
        "Cisco UCS firmware:BundleTypeCapProvider:dn managed
        object property"
    ::= { cucsFirmwareBundleTypeCapProviderEntry 2 }

cucsFirmwareBundleTypeCapProviderRn OBJECT-TYPE
    SYNTAX       SnmpAdminString
    MAX-ACCESS   read-only
    STATUS       current
    DESCRIPTION
        "Cisco UCS firmware:BundleTypeCapProvider:rn managed
        object property"
    ::= { cucsFirmwareBundleTypeCapProviderEntry 3 }

cucsFirmwareBundleTypeCapProviderDeleted OBJECT-TYPE
    SYNTAX       TruthValue
    MAX-ACCESS   read-only
    STATUS       current
    DESCRIPTION
        "Cisco UCS firmware:BundleTypeCapProvider:deleted
        managed object property"
    ::= { cucsFirmwareBundleTypeCapProviderEntry 4 }

cucsFirmwareBundleTypeCapProviderDeprecated OBJECT-TYPE
    SYNTAX       TruthValue
    MAX-ACCESS   read-only
    STATUS       current
    DESCRIPTION
        "Cisco UCS firmware:BundleTypeCapProvider:deprecated
        managed object property"
    ::= { cucsFirmwareBundleTypeCapProviderEntry 5 }

cucsFirmwareBundleTypeCapProviderGencount OBJECT-TYPE
    SYNTAX       Gauge32
    MAX-ACCESS   read-only
    STATUS       current
    DESCRIPTION
        "Cisco UCS firmware:BundleTypeCapProvider:gencount
        managed object property"
    ::= { cucsFirmwareBundleTypeCapProviderEntry 6 }

cucsFirmwareBundleTypeCapProviderMgmtPlaneVer OBJECT-TYPE
    SYNTAX       SnmpAdminString
    MAX-ACCESS   read-only
    STATUS       current
    DESCRIPTION
        "Cisco UCS firmware:BundleTypeCapProvider:mgmtPlaneVer
        managed object property"
    ::= { cucsFirmwareBundleTypeCapProviderEntry 7 }

cucsFirmwareBundleTypeCapProviderModel OBJECT-TYPE
    SYNTAX       SnmpAdminString
    MAX-ACCESS   read-only
    STATUS       current
    DESCRIPTION
        "Cisco UCS firmware:BundleTypeCapProvider:model
        managed object property"
    ::= { cucsFirmwareBundleTypeCapProviderEntry 8 }

cucsFirmwareBundleTypeCapProviderVendor OBJECT-TYPE
    SYNTAX       SnmpAdminString
    MAX-ACCESS   read-only
    STATUS       current
    DESCRIPTION
        "Cisco UCS firmware:BundleTypeCapProvider:vendor
        managed object property"
    ::= { cucsFirmwareBundleTypeCapProviderEntry 9 }

cucsFirmwareBundleTypeCapProviderElementLoadFailures OBJECT-TYPE
    SYNTAX       Gauge32
    MAX-ACCESS   read-only
    STATUS       current
    DESCRIPTION
        "Cisco UCS firmware:BundleTypeCapProvider:elementLoadFailures
        managed object property"
    ::= { cucsFirmwareBundleTypeCapProviderEntry 10 }

cucsFirmwareBundleTypeCapProviderElementsLoaded OBJECT-TYPE
    SYNTAX       Gauge32
    MAX-ACCESS   read-only
    STATUS       current
    DESCRIPTION
        "Cisco UCS firmware:BundleTypeCapProvider:elementsLoaded
        managed object property"
    ::= { cucsFirmwareBundleTypeCapProviderEntry 11 }

cucsFirmwareBundleTypeCapProviderLoadErrors OBJECT-TYPE
    SYNTAX       Gauge32
    MAX-ACCESS   read-only
    STATUS       current
    DESCRIPTION
        "Cisco UCS firmware:BundleTypeCapProvider:loadErrors
        managed object property"
    ::= { cucsFirmwareBundleTypeCapProviderEntry 12 }

cucsFirmwareBundleTypeCapProviderLoadWarnings OBJECT-TYPE
    SYNTAX       Gauge32
    MAX-ACCESS   read-only
    STATUS       current
    DESCRIPTION
        "Cisco UCS firmware:BundleTypeCapProvider:loadWarnings
        managed object property"
    ::= { cucsFirmwareBundleTypeCapProviderEntry 13 }

cucsFirmwareCatalogPackTable OBJECT-TYPE
    SYNTAX           SEQUENCE OF CucsFirmwareCatalogPackEntry
    MAX-ACCESS       not-accessible
    STATUS           current
    DESCRIPTION
        "Cisco UCS firmware:CatalogPack managed object table"
    ::= { cucsFirmwareObjects 29 }

cucsFirmwareCatalogPackEntry OBJECT-TYPE
    SYNTAX           CucsFirmwareCatalogPackEntry
    MAX-ACCESS       not-accessible
    STATUS           current
    DESCRIPTION
        "Entry for the cucsFirmwareCatalogPackTable table."
    INDEX { cucsFirmwareCatalogPackInstanceId }
    ::= { cucsFirmwareCatalogPackTable 1 }

CucsFirmwareCatalogPackEntry ::= SEQUENCE {
    cucsFirmwareCatalogPackInstanceId                                CucsManagedObjectId,
    cucsFirmwareCatalogPackDn                                        CucsManagedObjectDn,
    cucsFirmwareCatalogPackRn                                        SnmpAdminString,
    cucsFirmwareCatalogPackCatalogName                               SnmpAdminString,
    cucsFirmwareCatalogPackCatalogVersion                            SnmpAdminString,
    cucsFirmwareCatalogPackConfigState                               CucsFirmwareCatalogPackConfigState,
    cucsFirmwareCatalogPackConfigStatusMessage                       SnmpAdminString,
    cucsFirmwareCatalogPackDescr                                     SnmpAdminString,
    cucsFirmwareCatalogPackIntId                                     SnmpAdminString,
    cucsFirmwareCatalogPackMode                                      CucsFirmwarePackMode,
    cucsFirmwareCatalogPackName                                      SnmpAdminString,
    cucsFirmwareCatalogPackPolicyLevel                               Gauge32,
    cucsFirmwareCatalogPackPolicyOwner                               CucsPolicyPolicyOwner,
    cucsFirmwareCatalogPackStageSize                                 Gauge32,
    cucsFirmwareCatalogPackUpdateTrigger                             DateAndTime
}

cucsFirmwareCatalogPackInstanceId OBJECT-TYPE
    SYNTAX       CucsManagedObjectId
    MAX-ACCESS   not-accessible
    STATUS       current
    DESCRIPTION
        "Instance identifier of the managed object."
    ::= { cucsFirmwareCatalogPackEntry 1 }

cucsFirmwareCatalogPackDn OBJECT-TYPE
    SYNTAX       CucsManagedObjectDn
    MAX-ACCESS   read-only
    STATUS       current
    DESCRIPTION
        "Cisco UCS firmware:CatalogPack:dn managed object property"
    ::= { cucsFirmwareCatalogPackEntry 2 }

cucsFirmwareCatalogPackRn OBJECT-TYPE
    SYNTAX       SnmpAdminString
    MAX-ACCESS   read-only
    STATUS       current
    DESCRIPTION
        "Cisco UCS firmware:CatalogPack:rn managed object property"
    ::= { cucsFirmwareCatalogPackEntry 3 }

cucsFirmwareCatalogPackCatalogName OBJECT-TYPE
    SYNTAX       SnmpAdminString
    MAX-ACCESS   read-only
    STATUS       current
    DESCRIPTION
        "Cisco UCS firmware:CatalogPack:catalogName managed
        object property"
    ::= { cucsFirmwareCatalogPackEntry 4 }

cucsFirmwareCatalogPackCatalogVersion OBJECT-TYPE
    SYNTAX       SnmpAdminString
    MAX-ACCESS   read-only
    STATUS       current
    DESCRIPTION
        "Cisco UCS firmware:CatalogPack:catalogVersion
        managed object property"
    ::= { cucsFirmwareCatalogPackEntry 5 }

cucsFirmwareCatalogPackConfigState OBJECT-TYPE
    SYNTAX       CucsFirmwareCatalogPackConfigState
    MAX-ACCESS   read-only
    STATUS       current
    DESCRIPTION
        "Cisco UCS firmware:CatalogPack:configState managed
        object property"
    ::= { cucsFirmwareCatalogPackEntry 6 }

cucsFirmwareCatalogPackConfigStatusMessage OBJECT-TYPE
    SYNTAX       SnmpAdminString
    MAX-ACCESS   read-only
    STATUS       current
    DESCRIPTION
        "Cisco UCS firmware:CatalogPack:configStatusMessage
        managed object property"
    ::= { cucsFirmwareCatalogPackEntry 7 }

cucsFirmwareCatalogPackDescr OBJECT-TYPE
    SYNTAX       SnmpAdminString
    MAX-ACCESS   read-only
    STATUS       current
    DESCRIPTION
        "Cisco UCS firmware:CatalogPack:descr managed object property"
    ::= { cucsFirmwareCatalogPackEntry 8 }

cucsFirmwareCatalogPackIntId OBJECT-TYPE
    SYNTAX       SnmpAdminString
    MAX-ACCESS   read-only
    STATUS       current
    DESCRIPTION
        "Cisco UCS firmware:CatalogPack:intId managed object property"
    ::= { cucsFirmwareCatalogPackEntry 9 }

cucsFirmwareCatalogPackMode OBJECT-TYPE
    SYNTAX       CucsFirmwarePackMode
    MAX-ACCESS   read-only
    STATUS       current
    DESCRIPTION
        "Cisco UCS firmware:CatalogPack:mode managed object property"
    ::= { cucsFirmwareCatalogPackEntry 10 }

cucsFirmwareCatalogPackName OBJECT-TYPE
    SYNTAX       SnmpAdminString
    MAX-ACCESS   read-only
    STATUS       current
    DESCRIPTION
        "Cisco UCS firmware:CatalogPack:name managed object property"
    ::= { cucsFirmwareCatalogPackEntry 11 }

cucsFirmwareCatalogPackPolicyLevel OBJECT-TYPE
    SYNTAX       Gauge32
    MAX-ACCESS   read-only
    STATUS       current
    DESCRIPTION
        "Cisco UCS firmware:CatalogPack:policyLevel managed
        object property"
    ::= { cucsFirmwareCatalogPackEntry 12 }

cucsFirmwareCatalogPackPolicyOwner OBJECT-TYPE
    SYNTAX       CucsPolicyPolicyOwner
    MAX-ACCESS   read-only
    STATUS       current
    DESCRIPTION
        "Cisco UCS firmware:CatalogPack:policyOwner managed
        object property"
    ::= { cucsFirmwareCatalogPackEntry 13 }

cucsFirmwareCatalogPackStageSize OBJECT-TYPE
    SYNTAX       Gauge32
    MAX-ACCESS   read-only
    STATUS       current
    DESCRIPTION
        "Cisco UCS firmware:CatalogPack:stageSize managed object property"
    ::= { cucsFirmwareCatalogPackEntry 14 }

cucsFirmwareCatalogPackUpdateTrigger OBJECT-TYPE
    SYNTAX       DateAndTime
    MAX-ACCESS   read-only
    STATUS       current
    DESCRIPTION
        "Cisco UCS firmware:CatalogPack:updateTrigger managed
        object property"
    ::= { cucsFirmwareCatalogPackEntry 15 }

cucsFirmwareCatalogueTable OBJECT-TYPE
    SYNTAX           SEQUENCE OF CucsFirmwareCatalogueEntry
    MAX-ACCESS       not-accessible
    STATUS           current
    DESCRIPTION
        "Cisco UCS firmware:Catalogue managed object table"
    ::= { cucsFirmwareObjects 3 }

cucsFirmwareCatalogueEntry OBJECT-TYPE
    SYNTAX           CucsFirmwareCatalogueEntry
    MAX-ACCESS       not-accessible
    STATUS           current
    DESCRIPTION
        "Entry for the cucsFirmwareCatalogueTable table."
    INDEX { cucsFirmwareCatalogueInstanceId }
    ::= { cucsFirmwareCatalogueTable 1 }

CucsFirmwareCatalogueEntry ::= SEQUENCE {
    cucsFirmwareCatalogueInstanceId                                  CucsManagedObjectId,
    cucsFirmwareCatalogueDn                                          CucsManagedObjectDn,
    cucsFirmwareCatalogueRn                                          SnmpAdminString,
    cucsFirmwareCatalogueSyncTrigger                                 TruthValue
}

cucsFirmwareCatalogueInstanceId OBJECT-TYPE
    SYNTAX       CucsManagedObjectId
    MAX-ACCESS   not-accessible
    STATUS       current
    DESCRIPTION
        "Instance identifier of the managed object."
    ::= { cucsFirmwareCatalogueEntry 1 }

cucsFirmwareCatalogueDn OBJECT-TYPE
    SYNTAX       CucsManagedObjectDn
    MAX-ACCESS   read-only
    STATUS       current
    DESCRIPTION
        "Cisco UCS firmware:Catalogue:dn managed object property"
    ::= { cucsFirmwareCatalogueEntry 2 }

cucsFirmwareCatalogueRn OBJECT-TYPE
    SYNTAX       SnmpAdminString
    MAX-ACCESS   read-only
    STATUS       current
    DESCRIPTION
        "Cisco UCS firmware:Catalogue:rn managed object property"
    ::= { cucsFirmwareCatalogueEntry 3 }

cucsFirmwareCatalogueSyncTrigger OBJECT-TYPE
    SYNTAX       TruthValue
    MAX-ACCESS   read-only
    STATUS       current
    DESCRIPTION
        "Cisco UCS firmware:Catalogue:syncTrigger managed object property"
    ::= { cucsFirmwareCatalogueEntry 4 }

cucsFirmwareCompSourceTable OBJECT-TYPE
    SYNTAX           SEQUENCE OF CucsFirmwareCompSourceEntry
    MAX-ACCESS       not-accessible
    STATUS           current
    DESCRIPTION
        "Cisco UCS firmware:CompSource managed object table"
    ::= { cucsFirmwareObjects 4 }

cucsFirmwareCompSourceEntry OBJECT-TYPE
    SYNTAX           CucsFirmwareCompSourceEntry
    MAX-ACCESS       not-accessible
    STATUS           current
    DESCRIPTION
        "Entry for the cucsFirmwareCompSourceTable table."
    INDEX { cucsFirmwareCompSourceInstanceId }
    ::= { cucsFirmwareCompSourceTable 1 }

CucsFirmwareCompSourceEntry ::= SEQUENCE {
    cucsFirmwareCompSourceInstanceId                                 CucsManagedObjectId,
    cucsFirmwareCompSourceDn                                         CucsManagedObjectDn,
    cucsFirmwareCompSourceRn                                         SnmpAdminString,
    cucsFirmwareCompSourceInvTag                                     SnmpAdminString,
    cucsFirmwareCompSourceVersion                                    SnmpAdminString,
    cucsFirmwareCompSourceDescr                                      SnmpAdminString,
    cucsFirmwareCompSourceIntId                                      SnmpAdminString,
    cucsFirmwareCompSourceName                                       SnmpAdminString,
    cucsFirmwareCompSourcePolicyLevel                                Gauge32,
    cucsFirmwareCompSourcePolicyOwner                                CucsPolicyPolicyOwner
}

cucsFirmwareCompSourceInstanceId OBJECT-TYPE
    SYNTAX       CucsManagedObjectId
    MAX-ACCESS   not-accessible
    STATUS       current
    DESCRIPTION
        "Instance identifier of the managed object."
    ::= { cucsFirmwareCompSourceEntry 1 }

cucsFirmwareCompSourceDn OBJECT-TYPE
    SYNTAX       CucsManagedObjectDn
    MAX-ACCESS   read-only
    STATUS       current
    DESCRIPTION
        "Cisco UCS firmware:CompSource:dn managed object property"
    ::= { cucsFirmwareCompSourceEntry 2 }

cucsFirmwareCompSourceRn OBJECT-TYPE
    SYNTAX       SnmpAdminString
    MAX-ACCESS   read-only
    STATUS       current
    DESCRIPTION
        "Cisco UCS firmware:CompSource:rn managed object property"
    ::= { cucsFirmwareCompSourceEntry 3 }

cucsFirmwareCompSourceInvTag OBJECT-TYPE
    SYNTAX       SnmpAdminString
    MAX-ACCESS   read-only
    STATUS       current
    DESCRIPTION
        "Cisco UCS firmware:CompSource:invTag managed object property"
    ::= { cucsFirmwareCompSourceEntry 4 }

cucsFirmwareCompSourceVersion OBJECT-TYPE
    SYNTAX       SnmpAdminString
    MAX-ACCESS   read-only
    STATUS       current
    DESCRIPTION
        "Cisco UCS firmware:CompSource:version managed object property"
    ::= { cucsFirmwareCompSourceEntry 5 }

cucsFirmwareCompSourceDescr OBJECT-TYPE
    SYNTAX       SnmpAdminString
    MAX-ACCESS   read-only
    STATUS       current
    DESCRIPTION
        "Cisco UCS firmware:CompSource:descr managed object property"
    ::= { cucsFirmwareCompSourceEntry 6 }

cucsFirmwareCompSourceIntId OBJECT-TYPE
    SYNTAX       SnmpAdminString
    MAX-ACCESS   read-only
    STATUS       current
    DESCRIPTION
        "Cisco UCS firmware:CompSource:intId managed object property"
    ::= { cucsFirmwareCompSourceEntry 7 }

cucsFirmwareCompSourceName OBJECT-TYPE
    SYNTAX       SnmpAdminString
    MAX-ACCESS   read-only
    STATUS       current
    DESCRIPTION
        "Cisco UCS firmware:CompSource:name managed object property"
    ::= { cucsFirmwareCompSourceEntry 8 }

cucsFirmwareCompSourcePolicyLevel OBJECT-TYPE
    SYNTAX       Gauge32
    MAX-ACCESS   read-only
    STATUS       current
    DESCRIPTION
        "Cisco UCS firmware:CompSource:policyLevel managed
        object property"
    ::= { cucsFirmwareCompSourceEntry 9 }

cucsFirmwareCompSourcePolicyOwner OBJECT-TYPE
    SYNTAX       CucsPolicyPolicyOwner
    MAX-ACCESS   read-only
    STATUS       current
    DESCRIPTION
        "Cisco UCS firmware:CompSource:policyOwner managed
        object property"
    ::= { cucsFirmwareCompSourceEntry 10 }

cucsFirmwareCompTargetTable OBJECT-TYPE
    SYNTAX           SEQUENCE OF CucsFirmwareCompTargetEntry
    MAX-ACCESS       not-accessible
    STATUS           current
    DESCRIPTION
        "Cisco UCS firmware:CompTarget managed object table"
    ::= { cucsFirmwareObjects 5 }

cucsFirmwareCompTargetEntry OBJECT-TYPE
    SYNTAX           CucsFirmwareCompTargetEntry
    MAX-ACCESS       not-accessible
    STATUS           current
    DESCRIPTION
        "Entry for the cucsFirmwareCompTargetTable table."
    INDEX { cucsFirmwareCompTargetInstanceId }
    ::= { cucsFirmwareCompTargetTable 1 }

CucsFirmwareCompTargetEntry ::= SEQUENCE {
    cucsFirmwareCompTargetInstanceId                                 CucsManagedObjectId,
    cucsFirmwareCompTargetDn                                         CucsManagedObjectDn,
    cucsFirmwareCompTargetRn                                         SnmpAdminString,
    cucsFirmwareCompTargetInvTag                                     SnmpAdminString,
    cucsFirmwareCompTargetVersion                                    SnmpAdminString,
    cucsFirmwareCompTargetDescr                                      SnmpAdminString,
    cucsFirmwareCompTargetIntId                                      SnmpAdminString,
    cucsFirmwareCompTargetName                                       SnmpAdminString,
    cucsFirmwareCompTargetPolicyLevel                                Gauge32,
    cucsFirmwareCompTargetPolicyOwner                                CucsPolicyPolicyOwner
}

cucsFirmwareCompTargetInstanceId OBJECT-TYPE
    SYNTAX       CucsManagedObjectId
    MAX-ACCESS   not-accessible
    STATUS       current
    DESCRIPTION
        "Instance identifier of the managed object."
    ::= { cucsFirmwareCompTargetEntry 1 }

cucsFirmwareCompTargetDn OBJECT-TYPE
    SYNTAX       CucsManagedObjectDn
    MAX-ACCESS   read-only
    STATUS       current
    DESCRIPTION
        "Cisco UCS firmware:CompTarget:dn managed object property"
    ::= { cucsFirmwareCompTargetEntry 2 }

cucsFirmwareCompTargetRn OBJECT-TYPE
    SYNTAX       SnmpAdminString
    MAX-ACCESS   read-only
    STATUS       current
    DESCRIPTION
        "Cisco UCS firmware:CompTarget:rn managed object property"
    ::= { cucsFirmwareCompTargetEntry 3 }

cucsFirmwareCompTargetInvTag OBJECT-TYPE
    SYNTAX       SnmpAdminString
    MAX-ACCESS   read-only
    STATUS       current
    DESCRIPTION
        "Cisco UCS firmware:CompTarget:invTag managed object property"
    ::= { cucsFirmwareCompTargetEntry 4 }

cucsFirmwareCompTargetVersion OBJECT-TYPE
    SYNTAX       SnmpAdminString
    MAX-ACCESS   read-only
    STATUS       current
    DESCRIPTION
        "Cisco UCS firmware:CompTarget:version managed object property"
    ::= { cucsFirmwareCompTargetEntry 5 }

cucsFirmwareCompTargetDescr OBJECT-TYPE
    SYNTAX       SnmpAdminString
    MAX-ACCESS   read-only
    STATUS       current
    DESCRIPTION
        "Cisco UCS firmware:CompTarget:descr managed object property"
    ::= { cucsFirmwareCompTargetEntry 6 }

cucsFirmwareCompTargetIntId OBJECT-TYPE
    SYNTAX       SnmpAdminString
    MAX-ACCESS   read-only
    STATUS       current
    DESCRIPTION
        "Cisco UCS firmware:CompTarget:intId managed object property"
    ::= { cucsFirmwareCompTargetEntry 7 }

cucsFirmwareCompTargetName OBJECT-TYPE
    SYNTAX       SnmpAdminString
    MAX-ACCESS   read-only
    STATUS       current
    DESCRIPTION
        "Cisco UCS firmware:CompTarget:name managed object property"
    ::= { cucsFirmwareCompTargetEntry 8 }

cucsFirmwareCompTargetPolicyLevel OBJECT-TYPE
    SYNTAX       Gauge32
    MAX-ACCESS   read-only
    STATUS       current
    DESCRIPTION
        "Cisco UCS firmware:CompTarget:policyLevel managed
        object property"
    ::= { cucsFirmwareCompTargetEntry 9 }

cucsFirmwareCompTargetPolicyOwner OBJECT-TYPE
    SYNTAX       CucsPolicyPolicyOwner
    MAX-ACCESS   read-only
    STATUS       current
    DESCRIPTION
        "Cisco UCS firmware:CompTarget:policyOwner managed
        object property"
    ::= { cucsFirmwareCompTargetEntry 10 }

cucsFirmwareComputeHostPackTable OBJECT-TYPE
    SYNTAX           SEQUENCE OF CucsFirmwareComputeHostPackEntry
    MAX-ACCESS       not-accessible
    STATUS           current
    DESCRIPTION
        "Cisco UCS firmware:ComputeHostPack managed object table"
    ::= { cucsFirmwareObjects 6 }

cucsFirmwareComputeHostPackEntry OBJECT-TYPE
    SYNTAX           CucsFirmwareComputeHostPackEntry
    MAX-ACCESS       not-accessible
    STATUS           current
    DESCRIPTION
        "Entry for the cucsFirmwareComputeHostPackTable table."
    INDEX { cucsFirmwareComputeHostPackInstanceId }
    ::= { cucsFirmwareComputeHostPackTable 1 }

CucsFirmwareComputeHostPackEntry ::= SEQUENCE {
    cucsFirmwareComputeHostPackInstanceId                            CucsManagedObjectId,
    cucsFirmwareComputeHostPackDn                                    CucsManagedObjectDn,
    cucsFirmwareComputeHostPackRn                                    SnmpAdminString,
    cucsFirmwareComputeHostPackDescr                                 SnmpAdminString,
    cucsFirmwareComputeHostPackIntId                                 SnmpAdminString,
    cucsFirmwareComputeHostPackMode                                  CucsFirmwarePackMode,
    cucsFirmwareComputeHostPackName                                  SnmpAdminString,
    cucsFirmwareComputeHostPackStageSize                             Gauge32,
    cucsFirmwareComputeHostPackUpdateTrigger                         DateAndTime,
    cucsFirmwareComputeHostPackIgnoreCompCheck                       TruthValue,
    cucsFirmwareComputeHostPackConfigQualifier                       CucsFirmwareHostPackConfigQualifier,
    cucsFirmwareComputeHostPackBladeBundleName                       SnmpAdminString,
    cucsFirmwareComputeHostPackBladeBundleVersion                    SnmpAdminString,
    cucsFirmwareComputeHostPackPolicyLevel                           Gauge32,
    cucsFirmwareComputeHostPackPolicyOwner                           CucsPolicyPolicyOwner,
    cucsFirmwareComputeHostPackRackBundleName                        SnmpAdminString,
    cucsFirmwareComputeHostPackRackBundleVersion                     SnmpAdminString,
    cucsFirmwareComputeHostPackMSeriesBundleName                     SnmpAdminString,
    cucsFirmwareComputeHostPackMSeriesBundleVersion                  SnmpAdminString
}

cucsFirmwareComputeHostPackInstanceId OBJECT-TYPE
    SYNTAX       CucsManagedObjectId
    MAX-ACCESS   not-accessible
    STATUS       current
    DESCRIPTION
        "Instance identifier of the managed object."
    ::= { cucsFirmwareComputeHostPackEntry 1 }

cucsFirmwareComputeHostPackDn OBJECT-TYPE
    SYNTAX       CucsManagedObjectDn
    MAX-ACCESS   read-only
    STATUS       current
    DESCRIPTION
        "Cisco UCS firmware:ComputeHostPack:dn managed object property"
    ::= { cucsFirmwareComputeHostPackEntry 2 }

cucsFirmwareComputeHostPackRn OBJECT-TYPE
    SYNTAX       SnmpAdminString
    MAX-ACCESS   read-only
    STATUS       current
    DESCRIPTION
        "Cisco UCS firmware:ComputeHostPack:rn managed object property"
    ::= { cucsFirmwareComputeHostPackEntry 3 }

cucsFirmwareComputeHostPackDescr OBJECT-TYPE
    SYNTAX       SnmpAdminString
    MAX-ACCESS   read-only
    STATUS       current
    DESCRIPTION
        "Cisco UCS firmware:ComputeHostPack:descr managed object property"
    ::= { cucsFirmwareComputeHostPackEntry 4 }

cucsFirmwareComputeHostPackIntId OBJECT-TYPE
    SYNTAX       SnmpAdminString
    MAX-ACCESS   read-only
    STATUS       current
    DESCRIPTION
        "Cisco UCS firmware:ComputeHostPack:intId managed object property"
    ::= { cucsFirmwareComputeHostPackEntry 5 }

cucsFirmwareComputeHostPackMode OBJECT-TYPE
    SYNTAX       CucsFirmwarePackMode
    MAX-ACCESS   read-only
    STATUS       current
    DESCRIPTION
        "Cisco UCS firmware:ComputeHostPack:mode managed object property"
    ::= { cucsFirmwareComputeHostPackEntry 6 }

cucsFirmwareComputeHostPackName OBJECT-TYPE
    SYNTAX       SnmpAdminString
    MAX-ACCESS   read-only
    STATUS       current
    DESCRIPTION
        "Cisco UCS firmware:ComputeHostPack:name managed object property"
    ::= { cucsFirmwareComputeHostPackEntry 7 }

cucsFirmwareComputeHostPackStageSize OBJECT-TYPE
    SYNTAX       Gauge32
    MAX-ACCESS   read-only
    STATUS       current
    DESCRIPTION
        "Cisco UCS firmware:ComputeHostPack:stageSize managed
        object property"
    ::= { cucsFirmwareComputeHostPackEntry 8 }

cucsFirmwareComputeHostPackUpdateTrigger OBJECT-TYPE
    SYNTAX       DateAndTime
    MAX-ACCESS   read-only
    STATUS       current
    DESCRIPTION
        "Cisco UCS firmware:ComputeHostPack:updateTrigger
        managed object property"
    ::= { cucsFirmwareComputeHostPackEntry 9 }

cucsFirmwareComputeHostPackIgnoreCompCheck OBJECT-TYPE
    SYNTAX       TruthValue
    MAX-ACCESS   read-only
    STATUS       current
    DESCRIPTION
        "Cisco UCS firmware:ComputeHostPack:ignoreCompCheck
        managed object property"
    ::= { cucsFirmwareComputeHostPackEntry 10 }

cucsFirmwareComputeHostPackConfigQualifier OBJECT-TYPE
    SYNTAX       CucsFirmwareHostPackConfigQualifier
    MAX-ACCESS   read-only
    STATUS       current
    DESCRIPTION
        "Cisco UCS firmware:ComputeHostPack:configQualifier
        managed object property"
    ::= { cucsFirmwareComputeHostPackEntry 11 }

cucsFirmwareComputeHostPackBladeBundleName OBJECT-TYPE
    SYNTAX       SnmpAdminString
    MAX-ACCESS   read-only
    STATUS       current
    DESCRIPTION
        "Cisco UCS firmware:ComputeHostPack:bladeBundleName
        managed object property"
    ::= { cucsFirmwareComputeHostPackEntry 12 }

cucsFirmwareComputeHostPackBladeBundleVersion OBJECT-TYPE
    SYNTAX       SnmpAdminString
    MAX-ACCESS   read-only
    STATUS       current
    DESCRIPTION
        "Cisco UCS firmware:ComputeHostPack:bladeBundleVersion
        managed object property"
    ::= { cucsFirmwareComputeHostPackEntry 13 }

cucsFirmwareComputeHostPackPolicyLevel OBJECT-TYPE
    SYNTAX       Gauge32
    MAX-ACCESS   read-only
    STATUS       current
    DESCRIPTION
        "Cisco UCS firmware:ComputeHostPack:policyLevel
        managed object property"
    ::= { cucsFirmwareComputeHostPackEntry 14 }

cucsFirmwareComputeHostPackPolicyOwner OBJECT-TYPE
    SYNTAX       CucsPolicyPolicyOwner
    MAX-ACCESS   read-only
    STATUS       current
    DESCRIPTION
        "Cisco UCS firmware:ComputeHostPack:policyOwner
        managed object property"
    ::= { cucsFirmwareComputeHostPackEntry 15 }

cucsFirmwareComputeHostPackRackBundleName OBJECT-TYPE
    SYNTAX       SnmpAdminString
    MAX-ACCESS   read-only
    STATUS       current
    DESCRIPTION
        "Cisco UCS firmware:ComputeHostPack:rackBundleName
        managed object property"
    ::= { cucsFirmwareComputeHostPackEntry 16 }

cucsFirmwareComputeHostPackRackBundleVersion OBJECT-TYPE
    SYNTAX       SnmpAdminString
    MAX-ACCESS   read-only
    STATUS       current
    DESCRIPTION
        "Cisco UCS firmware:ComputeHostPack:rackBundleVersion
        managed object property"
    ::= { cucsFirmwareComputeHostPackEntry 17 }

cucsFirmwareComputeHostPackMSeriesBundleName OBJECT-TYPE
    SYNTAX       SnmpAdminString
    MAX-ACCESS   read-only
    STATUS       current
    DESCRIPTION
        "Cisco UCS firmware:ComputeHostPack:mSeriesBundleName
        managed object property"
    ::= { cucsFirmwareComputeHostPackEntry 19 }

cucsFirmwareComputeHostPackMSeriesBundleVersion OBJECT-TYPE
    SYNTAX       SnmpAdminString
    MAX-ACCESS   read-only
    STATUS       current
    DESCRIPTION
        "Cisco UCS firmware:ComputeHostPack:mSeriesBundleVersion
        managed object property"
    ::= { cucsFirmwareComputeHostPackEntry 20 }

cucsFirmwareComputeMgmtPackTable OBJECT-TYPE
    SYNTAX           SEQUENCE OF CucsFirmwareComputeMgmtPackEntry
    MAX-ACCESS       not-accessible
    STATUS           current
    DESCRIPTION
        "Cisco UCS firmware:ComputeMgmtPack managed object table"
    ::= { cucsFirmwareObjects 7 }

cucsFirmwareComputeMgmtPackEntry OBJECT-TYPE
    SYNTAX           CucsFirmwareComputeMgmtPackEntry
    MAX-ACCESS       not-accessible
    STATUS           current
    DESCRIPTION
        "Entry for the cucsFirmwareComputeMgmtPackTable table."
    INDEX { cucsFirmwareComputeMgmtPackInstanceId }
    ::= { cucsFirmwareComputeMgmtPackTable 1 }

CucsFirmwareComputeMgmtPackEntry ::= SEQUENCE {
    cucsFirmwareComputeMgmtPackInstanceId                            CucsManagedObjectId,
    cucsFirmwareComputeMgmtPackDn                                    CucsManagedObjectDn,
    cucsFirmwareComputeMgmtPackRn                                    SnmpAdminString,
    cucsFirmwareComputeMgmtPackDescr                                 SnmpAdminString,
    cucsFirmwareComputeMgmtPackIntId                                 SnmpAdminString,
    cucsFirmwareComputeMgmtPackMode                                  CucsFirmwarePackMode,
    cucsFirmwareComputeMgmtPackName                                  SnmpAdminString,
    cucsFirmwareComputeMgmtPackStageSize                             Gauge32,
    cucsFirmwareComputeMgmtPackUpdateTrigger                         DateAndTime,
    cucsFirmwareComputeMgmtPackIgnoreCompCheck                       TruthValue,
    cucsFirmwareComputeMgmtPackPolicyLevel                           Gauge32,
    cucsFirmwareComputeMgmtPackPolicyOwner                           CucsPolicyPolicyOwner
}

cucsFirmwareComputeMgmtPackInstanceId OBJECT-TYPE
    SYNTAX       CucsManagedObjectId
    MAX-ACCESS   not-accessible
    STATUS       current
    DESCRIPTION
        "Instance identifier of the managed object."
    ::= { cucsFirmwareComputeMgmtPackEntry 1 }

cucsFirmwareComputeMgmtPackDn OBJECT-TYPE
    SYNTAX       CucsManagedObjectDn
    MAX-ACCESS   read-only
    STATUS       current
    DESCRIPTION
        "Cisco UCS firmware:ComputeMgmtPack:dn managed object property"
    ::= { cucsFirmwareComputeMgmtPackEntry 2 }

cucsFirmwareComputeMgmtPackRn OBJECT-TYPE
    SYNTAX       SnmpAdminString
    MAX-ACCESS   read-only
    STATUS       current
    DESCRIPTION
        "Cisco UCS firmware:ComputeMgmtPack:rn managed object property"
    ::= { cucsFirmwareComputeMgmtPackEntry 3 }

cucsFirmwareComputeMgmtPackDescr OBJECT-TYPE
    SYNTAX       SnmpAdminString
    MAX-ACCESS   read-only
    STATUS       current
    DESCRIPTION
        "Cisco UCS firmware:ComputeMgmtPack:descr managed object property"
    ::= { cucsFirmwareComputeMgmtPackEntry 4 }

cucsFirmwareComputeMgmtPackIntId OBJECT-TYPE
    SYNTAX       SnmpAdminString
    MAX-ACCESS   read-only
    STATUS       current
    DESCRIPTION
        "Cisco UCS firmware:ComputeMgmtPack:intId managed object property"
    ::= { cucsFirmwareComputeMgmtPackEntry 5 }

cucsFirmwareComputeMgmtPackMode OBJECT-TYPE
    SYNTAX       CucsFirmwarePackMode
    MAX-ACCESS   read-only
    STATUS       current
    DESCRIPTION
        "Cisco UCS firmware:ComputeMgmtPack:mode managed object property"
    ::= { cucsFirmwareComputeMgmtPackEntry 6 }

cucsFirmwareComputeMgmtPackName OBJECT-TYPE
    SYNTAX       SnmpAdminString
    MAX-ACCESS   read-only
    STATUS       current
    DESCRIPTION
        "Cisco UCS firmware:ComputeMgmtPack:name managed object property"
    ::= { cucsFirmwareComputeMgmtPackEntry 7 }

cucsFirmwareComputeMgmtPackStageSize OBJECT-TYPE
    SYNTAX       Gauge32
    MAX-ACCESS   read-only
    STATUS       current
    DESCRIPTION
        "Cisco UCS firmware:ComputeMgmtPack:stageSize managed
        object property"
    ::= { cucsFirmwareComputeMgmtPackEntry 8 }

cucsFirmwareComputeMgmtPackUpdateTrigger OBJECT-TYPE
    SYNTAX       DateAndTime
    MAX-ACCESS   read-only
    STATUS       current
    DESCRIPTION
        "Cisco UCS firmware:ComputeMgmtPack:updateTrigger
        managed object property"
    ::= { cucsFirmwareComputeMgmtPackEntry 9 }

cucsFirmwareComputeMgmtPackIgnoreCompCheck OBJECT-TYPE
    SYNTAX       TruthValue
    MAX-ACCESS   read-only
    STATUS       current
    DESCRIPTION
        "Cisco UCS firmware:ComputeMgmtPack:ignoreCompCheck
        managed object property"
    ::= { cucsFirmwareComputeMgmtPackEntry 10 }

cucsFirmwareComputeMgmtPackPolicyLevel OBJECT-TYPE
    SYNTAX       Gauge32
    MAX-ACCESS   read-only
    STATUS       current
    DESCRIPTION
        "Cisco UCS firmware:ComputeMgmtPack:policyLevel
        managed object property"
    ::= { cucsFirmwareComputeMgmtPackEntry 11 }

cucsFirmwareComputeMgmtPackPolicyOwner OBJECT-TYPE
    SYNTAX       CucsPolicyPolicyOwner
    MAX-ACCESS   read-only
    STATUS       current
    DESCRIPTION
        "Cisco UCS firmware:ComputeMgmtPack:policyOwner
        managed object property"
    ::= { cucsFirmwareComputeMgmtPackEntry 12 }

cucsFirmwareConstraintTable OBJECT-TYPE
    SYNTAX           SEQUENCE OF CucsFirmwareConstraintEntry
    MAX-ACCESS       not-accessible
    STATUS           current
    DESCRIPTION
        "Cisco UCS firmware:Constraint managed object table"
    ::= { cucsFirmwareObjects 54 }

cucsFirmwareConstraintEntry OBJECT-TYPE
    SYNTAX           CucsFirmwareConstraintEntry
    MAX-ACCESS       not-accessible
    STATUS           current
    DESCRIPTION
        "Entry for the cucsFirmwareConstraintTable table."
    INDEX { cucsFirmwareConstraintInstanceId }
    ::= { cucsFirmwareConstraintTable 1 }

CucsFirmwareConstraintEntry ::= SEQUENCE {
    cucsFirmwareConstraintInstanceId                                 CucsManagedObjectId,
    cucsFirmwareConstraintDn                                         CucsManagedObjectDn,
    cucsFirmwareConstraintRn                                         SnmpAdminString,
    cucsFirmwareConstraintFeature                                    SnmpAdminString,
    cucsFirmwareConstraintMinBiosVersion                             SnmpAdminString,
    cucsFirmwareConstraintMinCimcVersion                             SnmpAdminString
}

cucsFirmwareConstraintInstanceId OBJECT-TYPE
    SYNTAX       CucsManagedObjectId
    MAX-ACCESS   not-accessible
    STATUS       current
    DESCRIPTION
        "Instance identifier of the managed object."
    ::= { cucsFirmwareConstraintEntry 1 }

cucsFirmwareConstraintDn OBJECT-TYPE
    SYNTAX       CucsManagedObjectDn
    MAX-ACCESS   read-only
    STATUS       current
    DESCRIPTION
        "Cisco UCS firmware:Constraint:dn managed object property"
    ::= { cucsFirmwareConstraintEntry 2 }

cucsFirmwareConstraintRn OBJECT-TYPE
    SYNTAX       SnmpAdminString
    MAX-ACCESS   read-only
    STATUS       current
    DESCRIPTION
        "Cisco UCS firmware:Constraint:rn managed object property"
    ::= { cucsFirmwareConstraintEntry 3 }

cucsFirmwareConstraintFeature OBJECT-TYPE
    SYNTAX       SnmpAdminString
    MAX-ACCESS   read-only
    STATUS       current
    DESCRIPTION
        "Cisco UCS firmware:Constraint:feature managed object property"
    ::= { cucsFirmwareConstraintEntry 4 }

cucsFirmwareConstraintMinBiosVersion OBJECT-TYPE
    SYNTAX       SnmpAdminString
    MAX-ACCESS   read-only
    STATUS       current
    DESCRIPTION
        "Cisco UCS firmware:Constraint:minBiosVersion managed
        object property"
    ::= { cucsFirmwareConstraintEntry 5 }

cucsFirmwareConstraintMinCimcVersion OBJECT-TYPE
    SYNTAX       SnmpAdminString
    MAX-ACCESS   read-only
    STATUS       current
    DESCRIPTION
        "Cisco UCS firmware:Constraint:minCimcVersion managed
        object property"
    ::= { cucsFirmwareConstraintEntry 6 }

cucsFirmwareConstraintsTable OBJECT-TYPE
    SYNTAX           SEQUENCE OF CucsFirmwareConstraintsEntry
    MAX-ACCESS       not-accessible
    STATUS           current
    DESCRIPTION
        "Cisco UCS firmware:Constraints managed object table"
    ::= { cucsFirmwareObjects 55 }

cucsFirmwareConstraintsEntry OBJECT-TYPE
    SYNTAX           CucsFirmwareConstraintsEntry
    MAX-ACCESS       not-accessible
    STATUS           current
    DESCRIPTION
        "Entry for the cucsFirmwareConstraintsTable table."
    INDEX { cucsFirmwareConstraintsInstanceId }
    ::= { cucsFirmwareConstraintsTable 1 }

CucsFirmwareConstraintsEntry ::= SEQUENCE {
    cucsFirmwareConstraintsInstanceId                                CucsManagedObjectId,
    cucsFirmwareConstraintsDn                                        CucsManagedObjectDn,
    cucsFirmwareConstraintsRn                                        SnmpAdminString
}

cucsFirmwareConstraintsInstanceId OBJECT-TYPE
    SYNTAX       CucsManagedObjectId
    MAX-ACCESS   not-accessible
    STATUS       current
    DESCRIPTION
        "Instance identifier of the managed object."
    ::= { cucsFirmwareConstraintsEntry 1 }

cucsFirmwareConstraintsDn OBJECT-TYPE
    SYNTAX       CucsManagedObjectDn
    MAX-ACCESS   read-only
    STATUS       current
    DESCRIPTION
        "Cisco UCS firmware:Constraints:dn managed object property"
    ::= { cucsFirmwareConstraintsEntry 2 }

cucsFirmwareConstraintsRn OBJECT-TYPE
    SYNTAX       SnmpAdminString
    MAX-ACCESS   read-only
    STATUS       current
    DESCRIPTION
        "Cisco UCS firmware:Constraints:rn managed object property"
    ::= { cucsFirmwareConstraintsEntry 3 }

cucsFirmwareDependencyTable OBJECT-TYPE
    SYNTAX           SEQUENCE OF CucsFirmwareDependencyEntry
    MAX-ACCESS       not-accessible
    STATUS           current
    DESCRIPTION
        "Cisco UCS firmware:Dependency managed object table"
    ::= { cucsFirmwareObjects 8 }

cucsFirmwareDependencyEntry OBJECT-TYPE
    SYNTAX           CucsFirmwareDependencyEntry
    MAX-ACCESS       not-accessible
    STATUS           current
    DESCRIPTION
        "Entry for the cucsFirmwareDependencyTable table."
    INDEX { cucsFirmwareDependencyInstanceId }
    ::= { cucsFirmwareDependencyTable 1 }

CucsFirmwareDependencyEntry ::= SEQUENCE {
    cucsFirmwareDependencyInstanceId                                 CucsManagedObjectId,
    cucsFirmwareDependencyDn                                         CucsManagedObjectDn,
    cucsFirmwareDependencyRn                                         SnmpAdminString,
    cucsFirmwareDependencyEp                                         CucsFirmwareType,
    cucsFirmwareDependencyHwModel                                    SnmpAdminString,
    cucsFirmwareDependencyHwRevision                                 SnmpAdminString,
    cucsFirmwareDependencyHwVendor                                   SnmpAdminString,
    cucsFirmwareDependencyInvTag                                     SnmpAdminString,
    cucsFirmwareDependencyMaxVer                                     SnmpAdminString,
    cucsFirmwareDependencyMinVer                                     SnmpAdminString,
    cucsFirmwareDependencyRelationship                               CucsFirmwareDependencyRelationship,
    cucsFirmwareDependencyScope                                      CucsFirmwareDependencyScope,
    cucsFirmwareDependencySensitivity                                CucsFirmwareDependencySensitivity
}

cucsFirmwareDependencyInstanceId OBJECT-TYPE
    SYNTAX       CucsManagedObjectId
    MAX-ACCESS   not-accessible
    STATUS       current
    DESCRIPTION
        "Instance identifier of the managed object."
    ::= { cucsFirmwareDependencyEntry 1 }

cucsFirmwareDependencyDn OBJECT-TYPE
    SYNTAX       CucsManagedObjectDn
    MAX-ACCESS   read-only
    STATUS       current
    DESCRIPTION
        "Cisco UCS firmware:Dependency:dn managed object property"
    ::= { cucsFirmwareDependencyEntry 2 }

cucsFirmwareDependencyRn OBJECT-TYPE
    SYNTAX       SnmpAdminString
    MAX-ACCESS   read-only
    STATUS       current
    DESCRIPTION
        "Cisco UCS firmware:Dependency:rn managed object property"
    ::= { cucsFirmwareDependencyEntry 3 }

cucsFirmwareDependencyEp OBJECT-TYPE
    SYNTAX       CucsFirmwareType
    MAX-ACCESS   read-only
    STATUS       current
    DESCRIPTION
        "Cisco UCS firmware:Dependency:ep managed object property"
    ::= { cucsFirmwareDependencyEntry 4 }

cucsFirmwareDependencyHwModel OBJECT-TYPE
    SYNTAX       SnmpAdminString
    MAX-ACCESS   read-only
    STATUS       current
    DESCRIPTION
        "Cisco UCS firmware:Dependency:hwModel managed object property"
    ::= { cucsFirmwareDependencyEntry 5 }

cucsFirmwareDependencyHwRevision OBJECT-TYPE
    SYNTAX       SnmpAdminString
    MAX-ACCESS   read-only
    STATUS       current
    DESCRIPTION
        "Cisco UCS firmware:Dependency:hwRevision managed object property"
    ::= { cucsFirmwareDependencyEntry 6 }

cucsFirmwareDependencyHwVendor OBJECT-TYPE
    SYNTAX       SnmpAdminString
    MAX-ACCESS   read-only
    STATUS       current
    DESCRIPTION
        "Cisco UCS firmware:Dependency:hwVendor managed object property"
    ::= { cucsFirmwareDependencyEntry 7 }

cucsFirmwareDependencyInvTag OBJECT-TYPE
    SYNTAX       SnmpAdminString
    MAX-ACCESS   read-only
    STATUS       current
    DESCRIPTION
        "Cisco UCS firmware:Dependency:invTag managed object property"
    ::= { cucsFirmwareDependencyEntry 8 }

cucsFirmwareDependencyMaxVer OBJECT-TYPE
    SYNTAX       SnmpAdminString
    MAX-ACCESS   read-only
    STATUS       current
    DESCRIPTION
        "Cisco UCS firmware:Dependency:maxVer managed object property"
    ::= { cucsFirmwareDependencyEntry 9 }

cucsFirmwareDependencyMinVer OBJECT-TYPE
    SYNTAX       SnmpAdminString
    MAX-ACCESS   read-only
    STATUS       current
    DESCRIPTION
        "Cisco UCS firmware:Dependency:minVer managed object property"
    ::= { cucsFirmwareDependencyEntry 10 }

cucsFirmwareDependencyRelationship OBJECT-TYPE
    SYNTAX       CucsFirmwareDependencyRelationship
    MAX-ACCESS   read-only
    STATUS       current
    DESCRIPTION
        "Cisco UCS firmware:Dependency:relationship managed
        object property"
    ::= { cucsFirmwareDependencyEntry 11 }

cucsFirmwareDependencyScope OBJECT-TYPE
    SYNTAX       CucsFirmwareDependencyScope
    MAX-ACCESS   read-only
    STATUS       current
    DESCRIPTION
        "Cisco UCS firmware:Dependency:scope managed object property"
    ::= { cucsFirmwareDependencyEntry 12 }

cucsFirmwareDependencySensitivity OBJECT-TYPE
    SYNTAX       CucsFirmwareDependencySensitivity
    MAX-ACCESS   read-only
    STATUS       current
    DESCRIPTION
        "Cisco UCS firmware:Dependency:sensitivity managed
        object property"
    ::= { cucsFirmwareDependencyEntry 13 }

cucsFirmwareDistImageTable OBJECT-TYPE
    SYNTAX           SEQUENCE OF CucsFirmwareDistImageEntry
    MAX-ACCESS       not-accessible
    STATUS           current
    DESCRIPTION
        "Cisco UCS firmware:DistImage managed object table"
    ::= { cucsFirmwareObjects 9 }

cucsFirmwareDistImageEntry OBJECT-TYPE
    SYNTAX           CucsFirmwareDistImageEntry
    MAX-ACCESS       not-accessible
    STATUS           current
    DESCRIPTION
        "Entry for the cucsFirmwareDistImageTable table."
    INDEX { cucsFirmwareDistImageInstanceId }
    ::= { cucsFirmwareDistImageTable 1 }

CucsFirmwareDistImageEntry ::= SEQUENCE {
    cucsFirmwareDistImageInstanceId                                  CucsManagedObjectId,
    cucsFirmwareDistImageDn                                          CucsManagedObjectDn,
    cucsFirmwareDistImageRn                                          SnmpAdminString,
    cucsFirmwareDistImageImageDeleted                                CucsFirmwareImageDeleted,
    cucsFirmwareDistImageName                                        SnmpAdminString,
    cucsFirmwareDistImageType                                        CucsFirmwareType
}

cucsFirmwareDistImageInstanceId OBJECT-TYPE
    SYNTAX       CucsManagedObjectId
    MAX-ACCESS   not-accessible
    STATUS       current
    DESCRIPTION
        "Instance identifier of the managed object."
    ::= { cucsFirmwareDistImageEntry 1 }

cucsFirmwareDistImageDn OBJECT-TYPE
    SYNTAX       CucsManagedObjectDn
    MAX-ACCESS   read-only
    STATUS       current
    DESCRIPTION
        "Cisco UCS firmware:DistImage:dn managed object property"
    ::= { cucsFirmwareDistImageEntry 2 }

cucsFirmwareDistImageRn OBJECT-TYPE
    SYNTAX       SnmpAdminString
    MAX-ACCESS   read-only
    STATUS       current
    DESCRIPTION
        "Cisco UCS firmware:DistImage:rn managed object property"
    ::= { cucsFirmwareDistImageEntry 3 }

cucsFirmwareDistImageImageDeleted OBJECT-TYPE
    SYNTAX       CucsFirmwareImageDeleted
    MAX-ACCESS   read-only
    STATUS       current
    DESCRIPTION
        "Cisco UCS firmware:DistImage:imageDeleted managed
        object property"
    ::= { cucsFirmwareDistImageEntry 4 }

cucsFirmwareDistImageName OBJECT-TYPE
    SYNTAX       SnmpAdminString
    MAX-ACCESS   read-only
    STATUS       current
    DESCRIPTION
        "Cisco UCS firmware:DistImage:name managed object property"
    ::= { cucsFirmwareDistImageEntry 5 }

cucsFirmwareDistImageType OBJECT-TYPE
    SYNTAX       CucsFirmwareType
    MAX-ACCESS   read-only
    STATUS       current
    DESCRIPTION
        "Cisco UCS firmware:DistImage:type managed object property"
    ::= { cucsFirmwareDistImageEntry 6 }

cucsFirmwareDistributableTable OBJECT-TYPE
    SYNTAX           SEQUENCE OF CucsFirmwareDistributableEntry
    MAX-ACCESS       not-accessible
    STATUS           current
    DESCRIPTION
        "Cisco UCS firmware:Distributable managed object table"
    ::= { cucsFirmwareObjects 10 }

cucsFirmwareDistributableEntry OBJECT-TYPE
    SYNTAX           CucsFirmwareDistributableEntry
    MAX-ACCESS       not-accessible
    STATUS           current
    DESCRIPTION
        "Entry for the cucsFirmwareDistributableTable table."
    INDEX { cucsFirmwareDistributableInstanceId }
    ::= { cucsFirmwareDistributableTable 1 }

CucsFirmwareDistributableEntry ::= SEQUENCE {
    cucsFirmwareDistributableInstanceId                              CucsManagedObjectId,
    cucsFirmwareDistributableDn                                      CucsManagedObjectDn,
    cucsFirmwareDistributableRn                                      SnmpAdminString,
    cucsFirmwareDistributableAdminState                              CucsFirmwareAdminState,
    cucsFirmwareDistributableCompleteness                            CucsFirmwareCompleteness,
    cucsFirmwareDistributableFsmDescr                                SnmpAdminString,
    cucsFirmwareDistributableFsmPrev                                 SnmpAdminString,
    cucsFirmwareDistributableFsmProgr                                Gauge32,
    cucsFirmwareDistributableFsmRmtInvErrCode                        Gauge32,
    cucsFirmwareDistributableFsmRmtInvErrDescr                       SnmpAdminString,
    cucsFirmwareDistributableFsmRmtInvRslt                           CucsConditionRemoteInvRslt,
    cucsFirmwareDistributableFsmStageDescr                           SnmpAdminString,
    cucsFirmwareDistributableFsmStamp                                DateAndTime,
    cucsFirmwareDistributableFsmStatus                               SnmpAdminString,
    cucsFirmwareDistributableFsmTry                                  Gauge32,
    cucsFirmwareDistributableImagePresence                           CucsFirmwareImagePresence,
    cucsFirmwareDistributableModel                                   SnmpAdminString,
    cucsFirmwareDistributableName                                    SnmpAdminString,
    cucsFirmwareDistributableTransferState                           CucsFirmwareTransferState,
    cucsFirmwareDistributableType                                    CucsFirmwareDistributableType,
    cucsFirmwareDistributableVendor                                  SnmpAdminString,
    cucsFirmwareDistributableVersion                                 SnmpAdminString,
    cucsFirmwareDistributableInvTag                                  SnmpAdminString,
    cucsFirmwareDistributableDescr                                   SnmpAdminString,
    cucsFirmwareDistributableIntId                                   SnmpAdminString,
    cucsFirmwareDistributablePolicyLevel                             Gauge32,
    cucsFirmwareDistributablePolicyOwner                             CucsPolicyPolicyOwner
}

cucsFirmwareDistributableInstanceId OBJECT-TYPE
    SYNTAX       CucsManagedObjectId
    MAX-ACCESS   not-accessible
    STATUS       current
    DESCRIPTION
        "Instance identifier of the managed object."
    ::= { cucsFirmwareDistributableEntry 1 }

cucsFirmwareDistributableDn OBJECT-TYPE
    SYNTAX       CucsManagedObjectDn
    MAX-ACCESS   read-only
    STATUS       current
    DESCRIPTION
        "Cisco UCS firmware:Distributable:dn managed object property"
    ::= { cucsFirmwareDistributableEntry 2 }

cucsFirmwareDistributableRn OBJECT-TYPE
    SYNTAX       SnmpAdminString
    MAX-ACCESS   read-only
    STATUS       current
    DESCRIPTION
        "Cisco UCS firmware:Distributable:rn managed object property"
    ::= { cucsFirmwareDistributableEntry 3 }

cucsFirmwareDistributableAdminState OBJECT-TYPE
    SYNTAX       CucsFirmwareAdminState
    MAX-ACCESS   read-only
    STATUS       current
    DESCRIPTION
        "Cisco UCS firmware:Distributable:adminState managed
        object property"
    ::= { cucsFirmwareDistributableEntry 4 }

cucsFirmwareDistributableCompleteness OBJECT-TYPE
    SYNTAX       CucsFirmwareCompleteness
    MAX-ACCESS   read-only
    STATUS       current
    DESCRIPTION
        "Cisco UCS firmware:Distributable:completeness
        managed object property"
    ::= { cucsFirmwareDistributableEntry 5 }

cucsFirmwareDistributableFsmDescr OBJECT-TYPE
    SYNTAX       SnmpAdminString
    MAX-ACCESS   read-only
    STATUS       current
    DESCRIPTION
        "Cisco UCS firmware:Distributable:fsmDescr managed
        object property"
    ::= { cucsFirmwareDistributableEntry 6 }

cucsFirmwareDistributableFsmPrev OBJECT-TYPE
    SYNTAX       SnmpAdminString
    MAX-ACCESS   read-only
    STATUS       current
    DESCRIPTION
        "Cisco UCS firmware:Distributable:fsmPrev managed object property"
    ::= { cucsFirmwareDistributableEntry 7 }

cucsFirmwareDistributableFsmProgr OBJECT-TYPE
    SYNTAX       Gauge32
    MAX-ACCESS   read-only
    STATUS       current
    DESCRIPTION
        "Cisco UCS firmware:Distributable:fsmProgr managed
        object property"
    ::= { cucsFirmwareDistributableEntry 8 }

cucsFirmwareDistributableFsmRmtInvErrCode OBJECT-TYPE
    SYNTAX       Gauge32
    MAX-ACCESS   read-only
    STATUS       current
    DESCRIPTION
        "Cisco UCS firmware:Distributable:fsmRmtInvErrCode
        managed object property"
    ::= { cucsFirmwareDistributableEntry 9 }

cucsFirmwareDistributableFsmRmtInvErrDescr OBJECT-TYPE
    SYNTAX       SnmpAdminString
    MAX-ACCESS   read-only
    STATUS       current
    DESCRIPTION
        "Cisco UCS firmware:Distributable:fsmRmtInvErrDescr
        managed object property"
    ::= { cucsFirmwareDistributableEntry 10 }

cucsFirmwareDistributableFsmRmtInvRslt OBJECT-TYPE
    SYNTAX       CucsConditionRemoteInvRslt
    MAX-ACCESS   read-only
    STATUS       current
    DESCRIPTION
        "Cisco UCS firmware:Distributable:fsmRmtInvRslt
        managed object property"
    ::= { cucsFirmwareDistributableEntry 11 }

cucsFirmwareDistributableFsmStageDescr OBJECT-TYPE
    SYNTAX       SnmpAdminString
    MAX-ACCESS   read-only
    STATUS       current
    DESCRIPTION
        "Cisco UCS firmware:Distributable:fsmStageDescr
        managed object property"
    ::= { cucsFirmwareDistributableEntry 12 }

cucsFirmwareDistributableFsmStamp OBJECT-TYPE
    SYNTAX       DateAndTime
    MAX-ACCESS   read-only
    STATUS       current
    DESCRIPTION
        "Cisco UCS firmware:Distributable:fsmStamp managed
        object property"
    ::= { cucsFirmwareDistributableEntry 13 }

cucsFirmwareDistributableFsmStatus OBJECT-TYPE
    SYNTAX       SnmpAdminString
    MAX-ACCESS   read-only
    STATUS       current
    DESCRIPTION
        "Cisco UCS firmware:Distributable:fsmStatus managed
        object property"
    ::= { cucsFirmwareDistributableEntry 14 }

cucsFirmwareDistributableFsmTry OBJECT-TYPE
    SYNTAX       Gauge32
    MAX-ACCESS   read-only
    STATUS       current
    DESCRIPTION
        "Cisco UCS firmware:Distributable:fsmTry managed object property"
    ::= { cucsFirmwareDistributableEntry 15 }

cucsFirmwareDistributableImagePresence OBJECT-TYPE
    SYNTAX       CucsFirmwareImagePresence
    MAX-ACCESS   read-only
    STATUS       current
    DESCRIPTION
        "Cisco UCS firmware:Distributable:imagePresence
        managed object property"
    ::= { cucsFirmwareDistributableEntry 16 }

cucsFirmwareDistributableModel OBJECT-TYPE
    SYNTAX       SnmpAdminString
    MAX-ACCESS   read-only
    STATUS       current
    DESCRIPTION
        "Cisco UCS firmware:Distributable:model managed object property"
    ::= { cucsFirmwareDistributableEntry 17 }

cucsFirmwareDistributableName OBJECT-TYPE
    SYNTAX       SnmpAdminString
    MAX-ACCESS   read-only
    STATUS       current
    DESCRIPTION
        "Cisco UCS firmware:Distributable:name managed object property"
    ::= { cucsFirmwareDistributableEntry 18 }

cucsFirmwareDistributableTransferState OBJECT-TYPE
    SYNTAX       CucsFirmwareTransferState
    MAX-ACCESS   read-only
    STATUS       current
    DESCRIPTION
        "Cisco UCS firmware:Distributable:transferState
        managed object property"
    ::= { cucsFirmwareDistributableEntry 19 }

cucsFirmwareDistributableType OBJECT-TYPE
    SYNTAX       CucsFirmwareDistributableType
    MAX-ACCESS   read-only
    STATUS       current
    DESCRIPTION
        "Cisco UCS firmware:Distributable:type managed object property"
    ::= { cucsFirmwareDistributableEntry 20 }

cucsFirmwareDistributableVendor OBJECT-TYPE
    SYNTAX       SnmpAdminString
    MAX-ACCESS   read-only
    STATUS       current
    DESCRIPTION
        "Cisco UCS firmware:Distributable:vendor managed object property"
    ::= { cucsFirmwareDistributableEntry 21 }

cucsFirmwareDistributableVersion OBJECT-TYPE
    SYNTAX       SnmpAdminString
    MAX-ACCESS   read-only
    STATUS       current
    DESCRIPTION
        "Cisco UCS firmware:Distributable:version managed object property"
    ::= { cucsFirmwareDistributableEntry 22 }

cucsFirmwareDistributableInvTag OBJECT-TYPE
    SYNTAX       SnmpAdminString
    MAX-ACCESS   read-only
    STATUS       current
    DESCRIPTION
        "Cisco UCS firmware:Distributable:invTag managed object property"
    ::= { cucsFirmwareDistributableEntry 23 }

cucsFirmwareDistributableDescr OBJECT-TYPE
    SYNTAX       SnmpAdminString
    MAX-ACCESS   read-only
    STATUS       current
    DESCRIPTION
        "Cisco UCS firmware:Distributable:descr managed object property"
    ::= { cucsFirmwareDistributableEntry 24 }

cucsFirmwareDistributableIntId OBJECT-TYPE
    SYNTAX       SnmpAdminString
    MAX-ACCESS   read-only
    STATUS       current
    DESCRIPTION
        "Cisco UCS firmware:Distributable:intId managed object property"
    ::= { cucsFirmwareDistributableEntry 25 }

cucsFirmwareDistributablePolicyLevel OBJECT-TYPE
    SYNTAX       Gauge32
    MAX-ACCESS   read-only
    STATUS       current
    DESCRIPTION
        "Cisco UCS firmware:Distributable:policyLevel managed
        object property"
    ::= { cucsFirmwareDistributableEntry 26 }

cucsFirmwareDistributablePolicyOwner OBJECT-TYPE
    SYNTAX       CucsPolicyPolicyOwner
    MAX-ACCESS   read-only
    STATUS       current
    DESCRIPTION
        "Cisco UCS firmware:Distributable:policyOwner managed
        object property"
    ::= { cucsFirmwareDistributableEntry 27 }

cucsFirmwareDistributableFsmTable OBJECT-TYPE
    SYNTAX           SEQUENCE OF CucsFirmwareDistributableFsmEntry
    MAX-ACCESS       not-accessible
    STATUS           current
    DESCRIPTION
        "Cisco UCS firmware:DistributableFsm managed object table"
    ::= { cucsFirmwareObjects 30 }

cucsFirmwareDistributableFsmEntry OBJECT-TYPE
    SYNTAX           CucsFirmwareDistributableFsmEntry
    MAX-ACCESS       not-accessible
    STATUS           current
    DESCRIPTION
        "Entry for the cucsFirmwareDistributableFsmTable table."
    INDEX { cucsFirmwareDistributableFsmInstanceId }
    ::= { cucsFirmwareDistributableFsmTable 1 }

CucsFirmwareDistributableFsmEntry ::= SEQUENCE {
    cucsFirmwareDistributableFsmInstanceId                           CucsManagedObjectId,
    cucsFirmwareDistributableFsmDn                                   CucsManagedObjectDn,
    cucsFirmwareDistributableFsmRn                                   SnmpAdminString,
    cucsFirmwareDistributableFsmCompletionTime                       DateAndTime,
    cucsFirmwareDistributableFsmCurrentFsm                           CucsFirmwareDistributableFsmCurrentFsm,
    cucsFirmwareDistributableFsmDescrData                            SnmpAdminString,
    cucsFirmwareDistributableFsmFsmStatus                            CucsFsmFsmStageStatus,
    cucsFirmwareDistributableFsmProgress                             Gauge32,
    cucsFirmwareDistributableFsmRmtErrCode                           Gauge32,
    cucsFirmwareDistributableFsmRmtErrDescr                          SnmpAdminString,
    cucsFirmwareDistributableFsmRmtRslt                              CucsConditionRemoteInvRslt
}

cucsFirmwareDistributableFsmInstanceId OBJECT-TYPE
    SYNTAX       CucsManagedObjectId
    MAX-ACCESS   not-accessible
    STATUS       current
    DESCRIPTION
        "Instance identifier of the managed object."
    ::= { cucsFirmwareDistributableFsmEntry 1 }

cucsFirmwareDistributableFsmDn OBJECT-TYPE
    SYNTAX       CucsManagedObjectDn
    MAX-ACCESS   read-only
    STATUS       current
    DESCRIPTION
        "Cisco UCS firmware:DistributableFsm:dn managed object property"
    ::= { cucsFirmwareDistributableFsmEntry 2 }

cucsFirmwareDistributableFsmRn OBJECT-TYPE
    SYNTAX       SnmpAdminString
    MAX-ACCESS   read-only
    STATUS       current
    DESCRIPTION
        "Cisco UCS firmware:DistributableFsm:rn managed object property"
    ::= { cucsFirmwareDistributableFsmEntry 3 }

cucsFirmwareDistributableFsmCompletionTime OBJECT-TYPE
    SYNTAX       DateAndTime
    MAX-ACCESS   read-only
    STATUS       current
    DESCRIPTION
        "Cisco UCS firmware:DistributableFsm:completionTime
        managed object property"
    ::= { cucsFirmwareDistributableFsmEntry 4 }

cucsFirmwareDistributableFsmCurrentFsm OBJECT-TYPE
    SYNTAX       CucsFirmwareDistributableFsmCurrentFsm
    MAX-ACCESS   read-only
    STATUS       current
    DESCRIPTION
        "Cisco UCS firmware:DistributableFsm:currentFsm
        managed object property"
    ::= { cucsFirmwareDistributableFsmEntry 5 }

cucsFirmwareDistributableFsmDescrData OBJECT-TYPE
    SYNTAX       SnmpAdminString
    MAX-ACCESS   read-only
    STATUS       current
    DESCRIPTION
        "Cisco UCS firmware:DistributableFsm:descr managed
        object property"
    ::= { cucsFirmwareDistributableFsmEntry 6 }

cucsFirmwareDistributableFsmFsmStatus OBJECT-TYPE
    SYNTAX       CucsFsmFsmStageStatus
    MAX-ACCESS   read-only
    STATUS       current
    DESCRIPTION
        "Cisco UCS firmware:DistributableFsm:fsmStatus
        managed object property"
    ::= { cucsFirmwareDistributableFsmEntry 7 }

cucsFirmwareDistributableFsmProgress OBJECT-TYPE
    SYNTAX       Gauge32
    MAX-ACCESS   read-only
    STATUS       current
    DESCRIPTION
        "Cisco UCS firmware:DistributableFsm:progress managed
        object property"
    ::= { cucsFirmwareDistributableFsmEntry 8 }

cucsFirmwareDistributableFsmRmtErrCode OBJECT-TYPE
    SYNTAX       Gauge32
    MAX-ACCESS   read-only
    STATUS       current
    DESCRIPTION
        "Cisco UCS firmware:DistributableFsm:rmtErrCode
        managed object property"
    ::= { cucsFirmwareDistributableFsmEntry 9 }

cucsFirmwareDistributableFsmRmtErrDescr OBJECT-TYPE
    SYNTAX       SnmpAdminString
    MAX-ACCESS   read-only
    STATUS       current
    DESCRIPTION
        "Cisco UCS firmware:DistributableFsm:rmtErrDescr
        managed object property"
    ::= { cucsFirmwareDistributableFsmEntry 10 }

cucsFirmwareDistributableFsmRmtRslt OBJECT-TYPE
    SYNTAX       CucsConditionRemoteInvRslt
    MAX-ACCESS   read-only
    STATUS       current
    DESCRIPTION
        "Cisco UCS firmware:DistributableFsm:rmtRslt managed
        object property"
    ::= { cucsFirmwareDistributableFsmEntry 11 }

cucsFirmwareDistributableFsmStageTable OBJECT-TYPE
    SYNTAX           SEQUENCE OF CucsFirmwareDistributableFsmStageEntry
    MAX-ACCESS       not-accessible
    STATUS           current
    DESCRIPTION
        "Cisco UCS firmware:DistributableFsmStage managed object table"
    ::= { cucsFirmwareObjects 31 }

cucsFirmwareDistributableFsmStageEntry OBJECT-TYPE
    SYNTAX           CucsFirmwareDistributableFsmStageEntry
    MAX-ACCESS       not-accessible
    STATUS           current
    DESCRIPTION
        "Entry for the cucsFirmwareDistributableFsmStageTable table."
    INDEX { cucsFirmwareDistributableFsmStageInstanceId }
    ::= { cucsFirmwareDistributableFsmStageTable 1 }

CucsFirmwareDistributableFsmStageEntry ::= SEQUENCE {
    cucsFirmwareDistributableFsmStageInstanceId                      CucsManagedObjectId,
    cucsFirmwareDistributableFsmStageDn                              CucsManagedObjectDn,
    cucsFirmwareDistributableFsmStageRn                              SnmpAdminString,
    cucsFirmwareDistributableFsmStageDescrData                       SnmpAdminString,
    cucsFirmwareDistributableFsmStageLastUpdateTime                  DateAndTime,
    cucsFirmwareDistributableFsmStageName                            CucsFirmwareDistributableFsmStageName,
    cucsFirmwareDistributableFsmStageOrder                           Gauge32,
    cucsFirmwareDistributableFsmStageRetry                           Gauge32,
    cucsFirmwareDistributableFsmStageStageStatus                     CucsFsmFsmStageStatus
}

cucsFirmwareDistributableFsmStageInstanceId OBJECT-TYPE
    SYNTAX       CucsManagedObjectId
    MAX-ACCESS   not-accessible
    STATUS       current
    DESCRIPTION
        "Instance identifier of the managed object."
    ::= { cucsFirmwareDistributableFsmStageEntry 1 }

cucsFirmwareDistributableFsmStageDn OBJECT-TYPE
    SYNTAX       CucsManagedObjectDn
    MAX-ACCESS   read-only
    STATUS       current
    DESCRIPTION
        "Cisco UCS firmware:DistributableFsmStage:dn managed
        object property"
    ::= { cucsFirmwareDistributableFsmStageEntry 2 }

cucsFirmwareDistributableFsmStageRn OBJECT-TYPE
    SYNTAX       SnmpAdminString
    MAX-ACCESS   read-only
    STATUS       current
    DESCRIPTION
        "Cisco UCS firmware:DistributableFsmStage:rn managed
        object property"
    ::= { cucsFirmwareDistributableFsmStageEntry 3 }

cucsFirmwareDistributableFsmStageDescrData OBJECT-TYPE
    SYNTAX       SnmpAdminString
    MAX-ACCESS   read-only
    STATUS       current
    DESCRIPTION
        "Cisco UCS firmware:DistributableFsmStage:descr
        managed object property"
    ::= { cucsFirmwareDistributableFsmStageEntry 4 }

cucsFirmwareDistributableFsmStageLastUpdateTime OBJECT-TYPE
    SYNTAX       DateAndTime
    MAX-ACCESS   read-only
    STATUS       current
    DESCRIPTION
        "Cisco UCS firmware:DistributableFsmStage:lastUpdateTime
        managed object property"
    ::= { cucsFirmwareDistributableFsmStageEntry 5 }

cucsFirmwareDistributableFsmStageName OBJECT-TYPE
    SYNTAX       CucsFirmwareDistributableFsmStageName
    MAX-ACCESS   read-only
    STATUS       current
    DESCRIPTION
        "Cisco UCS firmware:DistributableFsmStage:name
        managed object property"
    ::= { cucsFirmwareDistributableFsmStageEntry 6 }

cucsFirmwareDistributableFsmStageOrder OBJECT-TYPE
    SYNTAX       Gauge32
    MAX-ACCESS   read-only
    STATUS       current
    DESCRIPTION
        "Cisco UCS firmware:DistributableFsmStage:order
        managed object property"
    ::= { cucsFirmwareDistributableFsmStageEntry 7 }

cucsFirmwareDistributableFsmStageRetry OBJECT-TYPE
    SYNTAX       Gauge32
    MAX-ACCESS   read-only
    STATUS       current
    DESCRIPTION
        "Cisco UCS firmware:DistributableFsmStage:retry
        managed object property"
    ::= { cucsFirmwareDistributableFsmStageEntry 8 }

cucsFirmwareDistributableFsmStageStageStatus OBJECT-TYPE
    SYNTAX       CucsFsmFsmStageStatus
    MAX-ACCESS   read-only
    STATUS       current
    DESCRIPTION
        "Cisco UCS firmware:DistributableFsmStage:stageStatus
        managed object property"
    ::= { cucsFirmwareDistributableFsmStageEntry 9 }

cucsFirmwareDistributableFsmTaskTable OBJECT-TYPE
    SYNTAX           SEQUENCE OF CucsFirmwareDistributableFsmTaskEntry
    MAX-ACCESS       not-accessible
    STATUS           current
    DESCRIPTION
        "Cisco UCS firmware:DistributableFsmTask managed object table"
    ::= { cucsFirmwareObjects 11 }

cucsFirmwareDistributableFsmTaskEntry OBJECT-TYPE
    SYNTAX           CucsFirmwareDistributableFsmTaskEntry
    MAX-ACCESS       not-accessible
    STATUS           current
    DESCRIPTION
        "Entry for the cucsFirmwareDistributableFsmTaskTable table."
    INDEX { cucsFirmwareDistributableFsmTaskInstanceId }
    ::= { cucsFirmwareDistributableFsmTaskTable 1 }

CucsFirmwareDistributableFsmTaskEntry ::= SEQUENCE {
    cucsFirmwareDistributableFsmTaskInstanceId                       CucsManagedObjectId,
    cucsFirmwareDistributableFsmTaskDn                               CucsManagedObjectDn,
    cucsFirmwareDistributableFsmTaskRn                               SnmpAdminString,
    cucsFirmwareDistributableFsmTaskCompletion                       CucsFsmCompletion,
    cucsFirmwareDistributableFsmTaskFlags                            CucsFsmFlags,
    cucsFirmwareDistributableFsmTaskItem                             CucsFirmwareDistributableFsmTaskItem,
    cucsFirmwareDistributableFsmTaskSeqId                            Gauge32
}

cucsFirmwareDistributableFsmTaskInstanceId OBJECT-TYPE
    SYNTAX       CucsManagedObjectId
    MAX-ACCESS   not-accessible
    STATUS       current
    DESCRIPTION
        "Instance identifier of the managed object."
    ::= { cucsFirmwareDistributableFsmTaskEntry 1 }

cucsFirmwareDistributableFsmTaskDn OBJECT-TYPE
    SYNTAX       CucsManagedObjectDn
    MAX-ACCESS   read-only
    STATUS       current
    DESCRIPTION
        "Cisco UCS firmware:DistributableFsmTask:dn managed
        object property"
    ::= { cucsFirmwareDistributableFsmTaskEntry 2 }

cucsFirmwareDistributableFsmTaskRn OBJECT-TYPE
    SYNTAX       SnmpAdminString
    MAX-ACCESS   read-only
    STATUS       current
    DESCRIPTION
        "Cisco UCS firmware:DistributableFsmTask:rn managed
        object property"
    ::= { cucsFirmwareDistributableFsmTaskEntry 3 }

cucsFirmwareDistributableFsmTaskCompletion OBJECT-TYPE
    SYNTAX       CucsFsmCompletion
    MAX-ACCESS   read-only
    STATUS       current
    DESCRIPTION
        "Cisco UCS firmware:DistributableFsmTask:completion
        managed object property"
    ::= { cucsFirmwareDistributableFsmTaskEntry 4 }

cucsFirmwareDistributableFsmTaskFlags OBJECT-TYPE
    SYNTAX       CucsFsmFlags
    MAX-ACCESS   read-only
    STATUS       current
    DESCRIPTION
        "Cisco UCS firmware:DistributableFsmTask:flags
        managed object property"
    ::= { cucsFirmwareDistributableFsmTaskEntry 5 }

cucsFirmwareDistributableFsmTaskItem OBJECT-TYPE
    SYNTAX       CucsFirmwareDistributableFsmTaskItem
    MAX-ACCESS   read-only
    STATUS       current
    DESCRIPTION
        "Cisco UCS firmware:DistributableFsmTask:item managed
        object property"
    ::= { cucsFirmwareDistributableFsmTaskEntry 6 }

cucsFirmwareDistributableFsmTaskSeqId OBJECT-TYPE
    SYNTAX       Gauge32
    MAX-ACCESS   read-only
    STATUS       current
    DESCRIPTION
        "Cisco UCS firmware:DistributableFsmTask:seqId
        managed object property"
    ::= { cucsFirmwareDistributableFsmTaskEntry 7 }

cucsFirmwareDownloaderTable OBJECT-TYPE
    SYNTAX           SEQUENCE OF CucsFirmwareDownloaderEntry
    MAX-ACCESS       not-accessible
    STATUS           current
    DESCRIPTION
        "Cisco UCS firmware:Downloader managed object table"
    ::= { cucsFirmwareObjects 12 }

cucsFirmwareDownloaderEntry OBJECT-TYPE
    SYNTAX           CucsFirmwareDownloaderEntry
    MAX-ACCESS       not-accessible
    STATUS           current
    DESCRIPTION
        "Entry for the cucsFirmwareDownloaderTable table."
    INDEX { cucsFirmwareDownloaderInstanceId }
    ::= { cucsFirmwareDownloaderTable 1 }

CucsFirmwareDownloaderEntry ::= SEQUENCE {
    cucsFirmwareDownloaderInstanceId                                 CucsManagedObjectId,
    cucsFirmwareDownloaderDn                                         CucsManagedObjectDn,
    cucsFirmwareDownloaderRn                                         SnmpAdminString,
    cucsFirmwareDownloaderAdminState                                 CucsFirmwareDownloadActivity,
    cucsFirmwareDownloaderFileName                                   SnmpAdminString,
    cucsFirmwareDownloaderFsmDescr                                   SnmpAdminString,
    cucsFirmwareDownloaderFsmPrev                                    SnmpAdminString,
    cucsFirmwareDownloaderFsmProgr                                   Gauge32,
    cucsFirmwareDownloaderFsmRmtInvErrCode                           Gauge32,
    cucsFirmwareDownloaderFsmRmtInvErrDescr                          SnmpAdminString,
    cucsFirmwareDownloaderFsmRmtInvRslt                              CucsConditionRemoteInvRslt,
    cucsFirmwareDownloaderFsmStageDescr                              SnmpAdminString,
    cucsFirmwareDownloaderFsmStamp                                   DateAndTime,
    cucsFirmwareDownloaderFsmStatus                                  SnmpAdminString,
    cucsFirmwareDownloaderFsmTry                                     Gauge32,
    cucsFirmwareDownloaderImageSize                                  Gauge32,
    cucsFirmwareDownloaderProtocol                                   CucsFirmwareTransport,
    cucsFirmwareDownloaderPwd                                        SnmpAdminString,
    cucsFirmwareDownloaderRemotePath                                 SnmpAdminString,
    cucsFirmwareDownloaderServer                                     SnmpAdminString,
    cucsFirmwareDownloaderTransferState                              CucsFirmwareTransferState,
    cucsFirmwareDownloaderUser                                       SnmpAdminString
}

cucsFirmwareDownloaderInstanceId OBJECT-TYPE
    SYNTAX       CucsManagedObjectId
    MAX-ACCESS   not-accessible
    STATUS       current
    DESCRIPTION
        "Instance identifier of the managed object."
    ::= { cucsFirmwareDownloaderEntry 1 }

cucsFirmwareDownloaderDn OBJECT-TYPE
    SYNTAX       CucsManagedObjectDn
    MAX-ACCESS   read-only
    STATUS       current
    DESCRIPTION
        "Cisco UCS firmware:Downloader:dn managed object property"
    ::= { cucsFirmwareDownloaderEntry 2 }

cucsFirmwareDownloaderRn OBJECT-TYPE
    SYNTAX       SnmpAdminString
    MAX-ACCESS   read-only
    STATUS       current
    DESCRIPTION
        "Cisco UCS firmware:Downloader:rn managed object property"
    ::= { cucsFirmwareDownloaderEntry 3 }

cucsFirmwareDownloaderAdminState OBJECT-TYPE
    SYNTAX       CucsFirmwareDownloadActivity
    MAX-ACCESS   read-only
    STATUS       current
    DESCRIPTION
        "Cisco UCS firmware:Downloader:adminState managed object property"
    ::= { cucsFirmwareDownloaderEntry 4 }

cucsFirmwareDownloaderFileName OBJECT-TYPE
    SYNTAX       SnmpAdminString
    MAX-ACCESS   read-only
    STATUS       current
    DESCRIPTION
        "Cisco UCS firmware:Downloader:fileName managed object property"
    ::= { cucsFirmwareDownloaderEntry 5 }

cucsFirmwareDownloaderFsmDescr OBJECT-TYPE
    SYNTAX       SnmpAdminString
    MAX-ACCESS   read-only
    STATUS       current
    DESCRIPTION
        "Cisco UCS firmware:Downloader:fsmDescr managed object property"
    ::= { cucsFirmwareDownloaderEntry 6 }

cucsFirmwareDownloaderFsmPrev OBJECT-TYPE
    SYNTAX       SnmpAdminString
    MAX-ACCESS   read-only
    STATUS       current
    DESCRIPTION
        "Cisco UCS firmware:Downloader:fsmPrev managed object property"
    ::= { cucsFirmwareDownloaderEntry 7 }

cucsFirmwareDownloaderFsmProgr OBJECT-TYPE
    SYNTAX       Gauge32
    MAX-ACCESS   read-only
    STATUS       current
    DESCRIPTION
        "Cisco UCS firmware:Downloader:fsmProgr managed object property"
    ::= { cucsFirmwareDownloaderEntry 8 }

cucsFirmwareDownloaderFsmRmtInvErrCode OBJECT-TYPE
    SYNTAX       Gauge32
    MAX-ACCESS   read-only
    STATUS       current
    DESCRIPTION
        "Cisco UCS firmware:Downloader:fsmRmtInvErrCode
        managed object property"
    ::= { cucsFirmwareDownloaderEntry 9 }

cucsFirmwareDownloaderFsmRmtInvErrDescr OBJECT-TYPE
    SYNTAX       SnmpAdminString
    MAX-ACCESS   read-only
    STATUS       current
    DESCRIPTION
        "Cisco UCS firmware:Downloader:fsmRmtInvErrDescr
        managed object property"
    ::= { cucsFirmwareDownloaderEntry 10 }

cucsFirmwareDownloaderFsmRmtInvRslt OBJECT-TYPE
    SYNTAX       CucsConditionRemoteInvRslt
    MAX-ACCESS   read-only
    STATUS       current
    DESCRIPTION
        "Cisco UCS firmware:Downloader:fsmRmtInvRslt managed
        object property"
    ::= { cucsFirmwareDownloaderEntry 11 }

cucsFirmwareDownloaderFsmStageDescr OBJECT-TYPE
    SYNTAX       SnmpAdminString
    MAX-ACCESS   read-only
    STATUS       current
    DESCRIPTION
        "Cisco UCS firmware:Downloader:fsmStageDescr managed
        object property"
    ::= { cucsFirmwareDownloaderEntry 12 }

cucsFirmwareDownloaderFsmStamp OBJECT-TYPE
    SYNTAX       DateAndTime
    MAX-ACCESS   read-only
    STATUS       current
    DESCRIPTION
        "Cisco UCS firmware:Downloader:fsmStamp managed object property"
    ::= { cucsFirmwareDownloaderEntry 13 }

cucsFirmwareDownloaderFsmStatus OBJECT-TYPE
    SYNTAX       SnmpAdminString
    MAX-ACCESS   read-only
    STATUS       current
    DESCRIPTION
        "Cisco UCS firmware:Downloader:fsmStatus managed object property"
    ::= { cucsFirmwareDownloaderEntry 14 }

cucsFirmwareDownloaderFsmTry OBJECT-TYPE
    SYNTAX       Gauge32
    MAX-ACCESS   read-only
    STATUS       current
    DESCRIPTION
        "Cisco UCS firmware:Downloader:fsmTry managed object property"
    ::= { cucsFirmwareDownloaderEntry 15 }

cucsFirmwareDownloaderImageSize OBJECT-TYPE
    SYNTAX       Gauge32
    MAX-ACCESS   read-only
    STATUS       current
    DESCRIPTION
        "Cisco UCS firmware:Downloader:imageSize managed object property"
    ::= { cucsFirmwareDownloaderEntry 16 }

cucsFirmwareDownloaderProtocol OBJECT-TYPE
    SYNTAX       CucsFirmwareTransport
    MAX-ACCESS   read-only
    STATUS       current
    DESCRIPTION
        "Cisco UCS firmware:Downloader:protocol managed object property"
    ::= { cucsFirmwareDownloaderEntry 17 }

cucsFirmwareDownloaderPwd OBJECT-TYPE
    SYNTAX       SnmpAdminString
    MAX-ACCESS   read-only
    STATUS       current
    DESCRIPTION
        "Cisco UCS firmware:Downloader:pwd managed object property"
    ::= { cucsFirmwareDownloaderEntry 18 }

cucsFirmwareDownloaderRemotePath OBJECT-TYPE
    SYNTAX       SnmpAdminString
    MAX-ACCESS   read-only
    STATUS       current
    DESCRIPTION
        "Cisco UCS firmware:Downloader:remotePath managed object property"
    ::= { cucsFirmwareDownloaderEntry 19 }

cucsFirmwareDownloaderServer OBJECT-TYPE
    SYNTAX       SnmpAdminString
    MAX-ACCESS   read-only
    STATUS       current
    DESCRIPTION
        "Cisco UCS firmware:Downloader:server managed object property"
    ::= { cucsFirmwareDownloaderEntry 20 }

cucsFirmwareDownloaderTransferState OBJECT-TYPE
    SYNTAX       CucsFirmwareTransferState
    MAX-ACCESS   read-only
    STATUS       current
    DESCRIPTION
        "Cisco UCS firmware:Downloader:transferState managed
        object property"
    ::= { cucsFirmwareDownloaderEntry 21 }

cucsFirmwareDownloaderUser OBJECT-TYPE
    SYNTAX       SnmpAdminString
    MAX-ACCESS   read-only
    STATUS       current
    DESCRIPTION
        "Cisco UCS firmware:Downloader:user managed object property"
    ::= { cucsFirmwareDownloaderEntry 22 }

cucsFirmwareDownloaderFsmTable OBJECT-TYPE
    SYNTAX           SEQUENCE OF CucsFirmwareDownloaderFsmEntry
    MAX-ACCESS       not-accessible
    STATUS           current
    DESCRIPTION
        "Cisco UCS firmware:DownloaderFsm managed object table"
    ::= { cucsFirmwareObjects 32 }

cucsFirmwareDownloaderFsmEntry OBJECT-TYPE
    SYNTAX           CucsFirmwareDownloaderFsmEntry
    MAX-ACCESS       not-accessible
    STATUS           current
    DESCRIPTION
        "Entry for the cucsFirmwareDownloaderFsmTable table."
    INDEX { cucsFirmwareDownloaderFsmInstanceId }
    ::= { cucsFirmwareDownloaderFsmTable 1 }

CucsFirmwareDownloaderFsmEntry ::= SEQUENCE {
    cucsFirmwareDownloaderFsmInstanceId                              CucsManagedObjectId,
    cucsFirmwareDownloaderFsmDn                                      CucsManagedObjectDn,
    cucsFirmwareDownloaderFsmRn                                      SnmpAdminString,
    cucsFirmwareDownloaderFsmCompletionTime                          DateAndTime,
    cucsFirmwareDownloaderFsmCurrentFsm                              CucsFirmwareDownloaderFsmCurrentFsm,
    cucsFirmwareDownloaderFsmDescrData                               SnmpAdminString,
    cucsFirmwareDownloaderFsmFsmStatus                               CucsFsmFsmStageStatus,
    cucsFirmwareDownloaderFsmProgress                                Gauge32,
    cucsFirmwareDownloaderFsmRmtErrCode                              Gauge32,
    cucsFirmwareDownloaderFsmRmtErrDescr                             SnmpAdminString,
    cucsFirmwareDownloaderFsmRmtRslt                                 CucsConditionRemoteInvRslt
}

cucsFirmwareDownloaderFsmInstanceId OBJECT-TYPE
    SYNTAX       CucsManagedObjectId
    MAX-ACCESS   not-accessible
    STATUS       current
    DESCRIPTION
        "Instance identifier of the managed object."
    ::= { cucsFirmwareDownloaderFsmEntry 1 }

cucsFirmwareDownloaderFsmDn OBJECT-TYPE
    SYNTAX       CucsManagedObjectDn
    MAX-ACCESS   read-only
    STATUS       current
    DESCRIPTION
        "Cisco UCS firmware:DownloaderFsm:dn managed object property"
    ::= { cucsFirmwareDownloaderFsmEntry 2 }

cucsFirmwareDownloaderFsmRn OBJECT-TYPE
    SYNTAX       SnmpAdminString
    MAX-ACCESS   read-only
    STATUS       current
    DESCRIPTION
        "Cisco UCS firmware:DownloaderFsm:rn managed object property"
    ::= { cucsFirmwareDownloaderFsmEntry 3 }

cucsFirmwareDownloaderFsmCompletionTime OBJECT-TYPE
    SYNTAX       DateAndTime
    MAX-ACCESS   read-only
    STATUS       current
    DESCRIPTION
        "Cisco UCS firmware:DownloaderFsm:completionTime
        managed object property"
    ::= { cucsFirmwareDownloaderFsmEntry 4 }

cucsFirmwareDownloaderFsmCurrentFsm OBJECT-TYPE
    SYNTAX       CucsFirmwareDownloaderFsmCurrentFsm
    MAX-ACCESS   read-only
    STATUS       current
    DESCRIPTION
        "Cisco UCS firmware:DownloaderFsm:currentFsm managed
        object property"
    ::= { cucsFirmwareDownloaderFsmEntry 5 }

cucsFirmwareDownloaderFsmDescrData OBJECT-TYPE
    SYNTAX       SnmpAdminString
    MAX-ACCESS   read-only
    STATUS       current
    DESCRIPTION
        "Cisco UCS firmware:DownloaderFsm:descr managed object property"
    ::= { cucsFirmwareDownloaderFsmEntry 6 }

cucsFirmwareDownloaderFsmFsmStatus OBJECT-TYPE
    SYNTAX       CucsFsmFsmStageStatus
    MAX-ACCESS   read-only
    STATUS       current
    DESCRIPTION
        "Cisco UCS firmware:DownloaderFsm:fsmStatus managed
        object property"
    ::= { cucsFirmwareDownloaderFsmEntry 7 }

cucsFirmwareDownloaderFsmProgress OBJECT-TYPE
    SYNTAX       Gauge32
    MAX-ACCESS   read-only
    STATUS       current
    DESCRIPTION
        "Cisco UCS firmware:DownloaderFsm:progress managed
        object property"
    ::= { cucsFirmwareDownloaderFsmEntry 8 }

cucsFirmwareDownloaderFsmRmtErrCode OBJECT-TYPE
    SYNTAX       Gauge32
    MAX-ACCESS   read-only
    STATUS       current
    DESCRIPTION
        "Cisco UCS firmware:DownloaderFsm:rmtErrCode managed
        object property"
    ::= { cucsFirmwareDownloaderFsmEntry 9 }

cucsFirmwareDownloaderFsmRmtErrDescr OBJECT-TYPE
    SYNTAX       SnmpAdminString
    MAX-ACCESS   read-only
    STATUS       current
    DESCRIPTION
        "Cisco UCS firmware:DownloaderFsm:rmtErrDescr managed
        object property"
    ::= { cucsFirmwareDownloaderFsmEntry 10 }

cucsFirmwareDownloaderFsmRmtRslt OBJECT-TYPE
    SYNTAX       CucsConditionRemoteInvRslt
    MAX-ACCESS   read-only
    STATUS       current
    DESCRIPTION
        "Cisco UCS firmware:DownloaderFsm:rmtRslt managed object property"
    ::= { cucsFirmwareDownloaderFsmEntry 11 }

cucsFirmwareDownloaderFsmStageTable OBJECT-TYPE
    SYNTAX           SEQUENCE OF CucsFirmwareDownloaderFsmStageEntry
    MAX-ACCESS       not-accessible
    STATUS           current
    DESCRIPTION
        "Cisco UCS firmware:DownloaderFsmStage managed object table"
    ::= { cucsFirmwareObjects 33 }

cucsFirmwareDownloaderFsmStageEntry OBJECT-TYPE
    SYNTAX           CucsFirmwareDownloaderFsmStageEntry
    MAX-ACCESS       not-accessible
    STATUS           current
    DESCRIPTION
        "Entry for the cucsFirmwareDownloaderFsmStageTable table."
    INDEX { cucsFirmwareDownloaderFsmStageInstanceId }
    ::= { cucsFirmwareDownloaderFsmStageTable 1 }

CucsFirmwareDownloaderFsmStageEntry ::= SEQUENCE {
    cucsFirmwareDownloaderFsmStageInstanceId                         CucsManagedObjectId,
    cucsFirmwareDownloaderFsmStageDn                                 CucsManagedObjectDn,
    cucsFirmwareDownloaderFsmStageRn                                 SnmpAdminString,
    cucsFirmwareDownloaderFsmStageDescrData                          SnmpAdminString,
    cucsFirmwareDownloaderFsmStageLastUpdateTime                     DateAndTime,
    cucsFirmwareDownloaderFsmStageName                               CucsFirmwareDownloaderFsmStageName,
    cucsFirmwareDownloaderFsmStageOrder                              Gauge32,
    cucsFirmwareDownloaderFsmStageRetry                              Gauge32,
    cucsFirmwareDownloaderFsmStageStageStatus                        CucsFsmFsmStageStatus
}

cucsFirmwareDownloaderFsmStageInstanceId OBJECT-TYPE
    SYNTAX       CucsManagedObjectId
    MAX-ACCESS   not-accessible
    STATUS       current
    DESCRIPTION
        "Instance identifier of the managed object."
    ::= { cucsFirmwareDownloaderFsmStageEntry 1 }

cucsFirmwareDownloaderFsmStageDn OBJECT-TYPE
    SYNTAX       CucsManagedObjectDn
    MAX-ACCESS   read-only
    STATUS       current
    DESCRIPTION
        "Cisco UCS firmware:DownloaderFsmStage:dn managed object property"
    ::= { cucsFirmwareDownloaderFsmStageEntry 2 }

cucsFirmwareDownloaderFsmStageRn OBJECT-TYPE
    SYNTAX       SnmpAdminString
    MAX-ACCESS   read-only
    STATUS       current
    DESCRIPTION
        "Cisco UCS firmware:DownloaderFsmStage:rn managed object property"
    ::= { cucsFirmwareDownloaderFsmStageEntry 3 }

cucsFirmwareDownloaderFsmStageDescrData OBJECT-TYPE
    SYNTAX       SnmpAdminString
    MAX-ACCESS   read-only
    STATUS       current
    DESCRIPTION
        "Cisco UCS firmware:DownloaderFsmStage:descr managed
        object property"
    ::= { cucsFirmwareDownloaderFsmStageEntry 4 }

cucsFirmwareDownloaderFsmStageLastUpdateTime OBJECT-TYPE
    SYNTAX       DateAndTime
    MAX-ACCESS   read-only
    STATUS       current
    DESCRIPTION
        "Cisco UCS firmware:DownloaderFsmStage:lastUpdateTime
        managed object property"
    ::= { cucsFirmwareDownloaderFsmStageEntry 5 }

cucsFirmwareDownloaderFsmStageName OBJECT-TYPE
    SYNTAX       CucsFirmwareDownloaderFsmStageName
    MAX-ACCESS   read-only
    STATUS       current
    DESCRIPTION
        "Cisco UCS firmware:DownloaderFsmStage:name managed
        object property"
    ::= { cucsFirmwareDownloaderFsmStageEntry 6 }

cucsFirmwareDownloaderFsmStageOrder OBJECT-TYPE
    SYNTAX       Gauge32
    MAX-ACCESS   read-only
    STATUS       current
    DESCRIPTION
        "Cisco UCS firmware:DownloaderFsmStage:order managed
        object property"
    ::= { cucsFirmwareDownloaderFsmStageEntry 7 }

cucsFirmwareDownloaderFsmStageRetry OBJECT-TYPE
    SYNTAX       Gauge32
    MAX-ACCESS   read-only
    STATUS       current
    DESCRIPTION
        "Cisco UCS firmware:DownloaderFsmStage:retry managed
        object property"
    ::= { cucsFirmwareDownloaderFsmStageEntry 8 }

cucsFirmwareDownloaderFsmStageStageStatus OBJECT-TYPE
    SYNTAX       CucsFsmFsmStageStatus
    MAX-ACCESS   read-only
    STATUS       current
    DESCRIPTION
        "Cisco UCS firmware:DownloaderFsmStage:stageStatus
        managed object property"
    ::= { cucsFirmwareDownloaderFsmStageEntry 9 }

cucsFirmwareDownloaderFsmTaskTable OBJECT-TYPE
    SYNTAX           SEQUENCE OF CucsFirmwareDownloaderFsmTaskEntry
    MAX-ACCESS       not-accessible
    STATUS           current
    DESCRIPTION
        "Cisco UCS firmware:DownloaderFsmTask managed object table"
    ::= { cucsFirmwareObjects 13 }

cucsFirmwareDownloaderFsmTaskEntry OBJECT-TYPE
    SYNTAX           CucsFirmwareDownloaderFsmTaskEntry
    MAX-ACCESS       not-accessible
    STATUS           current
    DESCRIPTION
        "Entry for the cucsFirmwareDownloaderFsmTaskTable table."
    INDEX { cucsFirmwareDownloaderFsmTaskInstanceId }
    ::= { cucsFirmwareDownloaderFsmTaskTable 1 }

CucsFirmwareDownloaderFsmTaskEntry ::= SEQUENCE {
    cucsFirmwareDownloaderFsmTaskInstanceId                          CucsManagedObjectId,
    cucsFirmwareDownloaderFsmTaskDn                                  CucsManagedObjectDn,
    cucsFirmwareDownloaderFsmTaskRn                                  SnmpAdminString,
    cucsFirmwareDownloaderFsmTaskCompletion                          CucsFsmCompletion,
    cucsFirmwareDownloaderFsmTaskFlags                               CucsFsmFlags,
    cucsFirmwareDownloaderFsmTaskItem                                CucsFirmwareDownloaderFsmTaskItem,
    cucsFirmwareDownloaderFsmTaskSeqId                               Gauge32
}

cucsFirmwareDownloaderFsmTaskInstanceId OBJECT-TYPE
    SYNTAX       CucsManagedObjectId
    MAX-ACCESS   not-accessible
    STATUS       current
    DESCRIPTION
        "Instance identifier of the managed object."
    ::= { cucsFirmwareDownloaderFsmTaskEntry 1 }

cucsFirmwareDownloaderFsmTaskDn OBJECT-TYPE
    SYNTAX       CucsManagedObjectDn
    MAX-ACCESS   read-only
    STATUS       current
    DESCRIPTION
        "Cisco UCS firmware:DownloaderFsmTask:dn managed object property"
    ::= { cucsFirmwareDownloaderFsmTaskEntry 2 }

cucsFirmwareDownloaderFsmTaskRn OBJECT-TYPE
    SYNTAX       SnmpAdminString
    MAX-ACCESS   read-only
    STATUS       current
    DESCRIPTION
        "Cisco UCS firmware:DownloaderFsmTask:rn managed object property"
    ::= { cucsFirmwareDownloaderFsmTaskEntry 3 }

cucsFirmwareDownloaderFsmTaskCompletion OBJECT-TYPE
    SYNTAX       CucsFsmCompletion
    MAX-ACCESS   read-only
    STATUS       current
    DESCRIPTION
        "Cisco UCS firmware:DownloaderFsmTask:completion
        managed object property"
    ::= { cucsFirmwareDownloaderFsmTaskEntry 4 }

cucsFirmwareDownloaderFsmTaskFlags OBJECT-TYPE
    SYNTAX       CucsFsmFlags
    MAX-ACCESS   read-only
    STATUS       current
    DESCRIPTION
        "Cisco UCS firmware:DownloaderFsmTask:flags managed
        object property"
    ::= { cucsFirmwareDownloaderFsmTaskEntry 5 }

cucsFirmwareDownloaderFsmTaskItem OBJECT-TYPE
    SYNTAX       CucsFirmwareDownloaderFsmTaskItem
    MAX-ACCESS   read-only
    STATUS       current
    DESCRIPTION
        "Cisco UCS firmware:DownloaderFsmTask:item managed
        object property"
    ::= { cucsFirmwareDownloaderFsmTaskEntry 6 }

cucsFirmwareDownloaderFsmTaskSeqId OBJECT-TYPE
    SYNTAX       Gauge32
    MAX-ACCESS   read-only
    STATUS       current
    DESCRIPTION
        "Cisco UCS firmware:DownloaderFsmTask:seqId managed
        object property"
    ::= { cucsFirmwareDownloaderFsmTaskEntry 7 }

cucsFirmwareHostTable OBJECT-TYPE
    SYNTAX           SEQUENCE OF CucsFirmwareHostEntry
    MAX-ACCESS       not-accessible
    STATUS           current
    DESCRIPTION
        "Cisco UCS firmware:Host managed object table"
    ::= { cucsFirmwareObjects 34 }

cucsFirmwareHostEntry OBJECT-TYPE
    SYNTAX           CucsFirmwareHostEntry
    MAX-ACCESS       not-accessible
    STATUS           current
    DESCRIPTION
        "Entry for the cucsFirmwareHostTable table."
    INDEX { cucsFirmwareHostInstanceId }
    ::= { cucsFirmwareHostTable 1 }

CucsFirmwareHostEntry ::= SEQUENCE {
    cucsFirmwareHostInstanceId                                       CucsManagedObjectId,
    cucsFirmwareHostDn                                               CucsManagedObjectDn,
    cucsFirmwareHostRn                                               SnmpAdminString
}

cucsFirmwareHostInstanceId OBJECT-TYPE
    SYNTAX       CucsManagedObjectId
    MAX-ACCESS   not-accessible
    STATUS       current
    DESCRIPTION
        "Instance identifier of the managed object."
    ::= { cucsFirmwareHostEntry 1 }

cucsFirmwareHostDn OBJECT-TYPE
    SYNTAX       CucsManagedObjectDn
    MAX-ACCESS   read-only
    STATUS       current
    DESCRIPTION
        "Cisco UCS firmware:Host:dn managed object property"
    ::= { cucsFirmwareHostEntry 2 }

cucsFirmwareHostRn OBJECT-TYPE
    SYNTAX       SnmpAdminString
    MAX-ACCESS   read-only
    STATUS       current
    DESCRIPTION
        "Cisco UCS firmware:Host:rn managed object property"
    ::= { cucsFirmwareHostEntry 3 }

cucsFirmwareHostPackModImpactTable OBJECT-TYPE
    SYNTAX           SEQUENCE OF CucsFirmwareHostPackModImpactEntry
    MAX-ACCESS       not-accessible
    STATUS           current
    DESCRIPTION
        "Cisco UCS firmware:HostPackModImpact managed object table"
    ::= { cucsFirmwareObjects 35 }

cucsFirmwareHostPackModImpactEntry OBJECT-TYPE
    SYNTAX           CucsFirmwareHostPackModImpactEntry
    MAX-ACCESS       not-accessible
    STATUS           current
    DESCRIPTION
        "Entry for the cucsFirmwareHostPackModImpactTable table."
    INDEX { cucsFirmwareHostPackModImpactInstanceId }
    ::= { cucsFirmwareHostPackModImpactTable 1 }

CucsFirmwareHostPackModImpactEntry ::= SEQUENCE {
    cucsFirmwareHostPackModImpactInstanceId                          CucsManagedObjectId,
    cucsFirmwareHostPackModImpactDn                                  CucsManagedObjectDn,
    cucsFirmwareHostPackModImpactRn                                  SnmpAdminString,
    cucsFirmwareHostPackModImpactKeyDn                               SnmpAdminString,
    cucsFirmwareHostPackModImpactMaintPolicyDn                       SnmpAdminString,
    cucsFirmwareHostPackModImpactPnDn                                SnmpAdminString,
    cucsFirmwareHostPackModImpactRebootPolicy                        SnmpAdminString,
    cucsFirmwareHostPackModImpactServiceProfileDn                    SnmpAdminString
}

cucsFirmwareHostPackModImpactInstanceId OBJECT-TYPE
    SYNTAX       CucsManagedObjectId
    MAX-ACCESS   not-accessible
    STATUS       current
    DESCRIPTION
        "Instance identifier of the managed object."
    ::= { cucsFirmwareHostPackModImpactEntry 1 }

cucsFirmwareHostPackModImpactDn OBJECT-TYPE
    SYNTAX       CucsManagedObjectDn
    MAX-ACCESS   read-only
    STATUS       current
    DESCRIPTION
        "Cisco UCS firmware:HostPackModImpact:dn managed object property"
    ::= { cucsFirmwareHostPackModImpactEntry 2 }

cucsFirmwareHostPackModImpactRn OBJECT-TYPE
    SYNTAX       SnmpAdminString
    MAX-ACCESS   read-only
    STATUS       current
    DESCRIPTION
        "Cisco UCS firmware:HostPackModImpact:rn managed object property"
    ::= { cucsFirmwareHostPackModImpactEntry 3 }

cucsFirmwareHostPackModImpactKeyDn OBJECT-TYPE
    SYNTAX       SnmpAdminString
    MAX-ACCESS   read-only
    STATUS       current
    DESCRIPTION
        "Cisco UCS firmware:HostPackModImpact:keyDn managed
        object property"
    ::= { cucsFirmwareHostPackModImpactEntry 4 }

cucsFirmwareHostPackModImpactMaintPolicyDn OBJECT-TYPE
    SYNTAX       SnmpAdminString
    MAX-ACCESS   read-only
    STATUS       current
    DESCRIPTION
        "Cisco UCS firmware:HostPackModImpact:maintPolicyDn
        managed object property"
    ::= { cucsFirmwareHostPackModImpactEntry 5 }

cucsFirmwareHostPackModImpactPnDn OBJECT-TYPE
    SYNTAX       SnmpAdminString
    MAX-ACCESS   read-only
    STATUS       current
    DESCRIPTION
        "Cisco UCS firmware:HostPackModImpact:pnDn managed
        object property"
    ::= { cucsFirmwareHostPackModImpactEntry 6 }

cucsFirmwareHostPackModImpactRebootPolicy OBJECT-TYPE
    SYNTAX       SnmpAdminString
    MAX-ACCESS   read-only
    STATUS       current
    DESCRIPTION
        "Cisco UCS firmware:HostPackModImpact:rebootPolicy
        managed object property"
    ::= { cucsFirmwareHostPackModImpactEntry 7 }

cucsFirmwareHostPackModImpactServiceProfileDn OBJECT-TYPE
    SYNTAX       SnmpAdminString
    MAX-ACCESS   read-only
    STATUS       current
    DESCRIPTION
        "Cisco UCS firmware:HostPackModImpact:serviceProfileDn
        managed object property"
    ::= { cucsFirmwareHostPackModImpactEntry 8 }

cucsFirmwareImageTable OBJECT-TYPE
    SYNTAX           SEQUENCE OF CucsFirmwareImageEntry
    MAX-ACCESS       not-accessible
    STATUS           current
    DESCRIPTION
        "Cisco UCS firmware:Image managed object table"
    ::= { cucsFirmwareObjects 14 }

cucsFirmwareImageEntry OBJECT-TYPE
    SYNTAX           CucsFirmwareImageEntry
    MAX-ACCESS       not-accessible
    STATUS           current
    DESCRIPTION
        "Entry for the cucsFirmwareImageTable table."
    INDEX { cucsFirmwareImageInstanceId }
    ::= { cucsFirmwareImageTable 1 }

CucsFirmwareImageEntry ::= SEQUENCE {
    cucsFirmwareImageInstanceId                                      CucsManagedObjectId,
    cucsFirmwareImageDn                                              CucsManagedObjectDn,
    cucsFirmwareImageRn                                              SnmpAdminString,
    cucsFirmwareImageAdminState                                      CucsFirmwareAdminState,
    cucsFirmwareImageChecksum                                        SnmpAdminString,
    cucsFirmwareImageDownloadDate                                    DateAndTime,
    cucsFirmwareImageFsmDescr                                        SnmpAdminString,
    cucsFirmwareImageFsmPrev                                         SnmpAdminString,
    cucsFirmwareImageFsmProgr                                        Gauge32,
    cucsFirmwareImageFsmRmtInvErrCode                                Gauge32,
    cucsFirmwareImageFsmRmtInvErrDescr                               SnmpAdminString,
    cucsFirmwareImageFsmRmtInvRslt                                   CucsConditionRemoteInvRslt,
    cucsFirmwareImageFsmStageDescr                                   SnmpAdminString,
    cucsFirmwareImageFsmStamp                                        DateAndTime,
    cucsFirmwareImageFsmStatus                                       SnmpAdminString,
    cucsFirmwareImageFsmTry                                          Gauge32,
    cucsFirmwareImageImagePresence                                   CucsFirmwareImagePresence,
    cucsFirmwareImageInvTag                                          SnmpAdminString,
    cucsFirmwareImageIsoname                                         SnmpAdminString,
    cucsFirmwareImageLocation                                        SnmpAdminString,
    cucsFirmwareImageName                                            SnmpAdminString,
    cucsFirmwareImageSize                                            Gauge32,
    cucsFirmwareImageType                                            CucsFirmwareType,
    cucsFirmwareImageVersion                                         SnmpAdminString,
    cucsFirmwareImageDescr                                           SnmpAdminString,
    cucsFirmwareImageIntId                                           SnmpAdminString,
    cucsFirmwareImagePolicyLevel                                     Gauge32,
    cucsFirmwareImagePolicyOwner                                     CucsPolicyPolicyOwner
}

cucsFirmwareImageInstanceId OBJECT-TYPE
    SYNTAX       CucsManagedObjectId
    MAX-ACCESS   not-accessible
    STATUS       current
    DESCRIPTION
        "Instance identifier of the managed object."
    ::= { cucsFirmwareImageEntry 1 }

cucsFirmwareImageDn OBJECT-TYPE
    SYNTAX       CucsManagedObjectDn
    MAX-ACCESS   read-only
    STATUS       current
    DESCRIPTION
        "Cisco UCS firmware:Image:dn managed object property"
    ::= { cucsFirmwareImageEntry 2 }

cucsFirmwareImageRn OBJECT-TYPE
    SYNTAX       SnmpAdminString
    MAX-ACCESS   read-only
    STATUS       current
    DESCRIPTION
        "Cisco UCS firmware:Image:rn managed object property"
    ::= { cucsFirmwareImageEntry 3 }

cucsFirmwareImageAdminState OBJECT-TYPE
    SYNTAX       CucsFirmwareAdminState
    MAX-ACCESS   read-only
    STATUS       current
    DESCRIPTION
        "Cisco UCS firmware:Image:adminState managed object property"
    ::= { cucsFirmwareImageEntry 4 }

cucsFirmwareImageChecksum OBJECT-TYPE
    SYNTAX       SnmpAdminString
    MAX-ACCESS   read-only
    STATUS       current
    DESCRIPTION
        "Cisco UCS firmware:Image:checksum managed object property"
    ::= { cucsFirmwareImageEntry 5 }

cucsFirmwareImageDownloadDate OBJECT-TYPE
    SYNTAX       DateAndTime
    MAX-ACCESS   read-only
    STATUS       current
    DESCRIPTION
        "Cisco UCS firmware:Image:downloadDate managed object property"
    ::= { cucsFirmwareImageEntry 6 }

cucsFirmwareImageFsmDescr OBJECT-TYPE
    SYNTAX       SnmpAdminString
    MAX-ACCESS   read-only
    STATUS       current
    DESCRIPTION
        "Cisco UCS firmware:Image:fsmDescr managed object property"
    ::= { cucsFirmwareImageEntry 7 }

cucsFirmwareImageFsmPrev OBJECT-TYPE
    SYNTAX       SnmpAdminString
    MAX-ACCESS   read-only
    STATUS       current
    DESCRIPTION
        "Cisco UCS firmware:Image:fsmPrev managed object property"
    ::= { cucsFirmwareImageEntry 8 }

cucsFirmwareImageFsmProgr OBJECT-TYPE
    SYNTAX       Gauge32
    MAX-ACCESS   read-only
    STATUS       current
    DESCRIPTION
        "Cisco UCS firmware:Image:fsmProgr managed object property"
    ::= { cucsFirmwareImageEntry 9 }

cucsFirmwareImageFsmRmtInvErrCode OBJECT-TYPE
    SYNTAX       Gauge32
    MAX-ACCESS   read-only
    STATUS       current
    DESCRIPTION
        "Cisco UCS firmware:Image:fsmRmtInvErrCode managed
        object property"
    ::= { cucsFirmwareImageEntry 10 }

cucsFirmwareImageFsmRmtInvErrDescr OBJECT-TYPE
    SYNTAX       SnmpAdminString
    MAX-ACCESS   read-only
    STATUS       current
    DESCRIPTION
        "Cisco UCS firmware:Image:fsmRmtInvErrDescr managed
        object property"
    ::= { cucsFirmwareImageEntry 11 }

cucsFirmwareImageFsmRmtInvRslt OBJECT-TYPE
    SYNTAX       CucsConditionRemoteInvRslt
    MAX-ACCESS   read-only
    STATUS       current
    DESCRIPTION
        "Cisco UCS firmware:Image:fsmRmtInvRslt managed object property"
    ::= { cucsFirmwareImageEntry 12 }

cucsFirmwareImageFsmStageDescr OBJECT-TYPE
    SYNTAX       SnmpAdminString
    MAX-ACCESS   read-only
    STATUS       current
    DESCRIPTION
        "Cisco UCS firmware:Image:fsmStageDescr managed object property"
    ::= { cucsFirmwareImageEntry 13 }

cucsFirmwareImageFsmStamp OBJECT-TYPE
    SYNTAX       DateAndTime
    MAX-ACCESS   read-only
    STATUS       current
    DESCRIPTION
        "Cisco UCS firmware:Image:fsmStamp managed object property"
    ::= { cucsFirmwareImageEntry 14 }

cucsFirmwareImageFsmStatus OBJECT-TYPE
    SYNTAX       SnmpAdminString
    MAX-ACCESS   read-only
    STATUS       current
    DESCRIPTION
        "Cisco UCS firmware:Image:fsmStatus managed object property"
    ::= { cucsFirmwareImageEntry 15 }

cucsFirmwareImageFsmTry OBJECT-TYPE
    SYNTAX       Gauge32
    MAX-ACCESS   read-only
    STATUS       current
    DESCRIPTION
        "Cisco UCS firmware:Image:fsmTry managed object property"
    ::= { cucsFirmwareImageEntry 16 }

cucsFirmwareImageImagePresence OBJECT-TYPE
    SYNTAX       CucsFirmwareImagePresence
    MAX-ACCESS   read-only
    STATUS       current
    DESCRIPTION
        "Cisco UCS firmware:Image:imagePresence managed object property"
    ::= { cucsFirmwareImageEntry 17 }

cucsFirmwareImageInvTag OBJECT-TYPE
    SYNTAX       SnmpAdminString
    MAX-ACCESS   read-only
    STATUS       current
    DESCRIPTION
        "Cisco UCS firmware:Image:invTag managed object property"
    ::= { cucsFirmwareImageEntry 18 }

cucsFirmwareImageIsoname OBJECT-TYPE
    SYNTAX       SnmpAdminString
    MAX-ACCESS   read-only
    STATUS       current
    DESCRIPTION
        "Cisco UCS firmware:Image:isoname managed object property"
    ::= { cucsFirmwareImageEntry 19 }

cucsFirmwareImageLocation OBJECT-TYPE
    SYNTAX       SnmpAdminString
    MAX-ACCESS   read-only
    STATUS       current
    DESCRIPTION
        "Cisco UCS firmware:Image:location managed object property"
    ::= { cucsFirmwareImageEntry 20 }

cucsFirmwareImageName OBJECT-TYPE
    SYNTAX       SnmpAdminString
    MAX-ACCESS   read-only
    STATUS       current
    DESCRIPTION
        "Cisco UCS firmware:Image:name managed object property"
    ::= { cucsFirmwareImageEntry 21 }

cucsFirmwareImageSize OBJECT-TYPE
    SYNTAX       Gauge32
    MAX-ACCESS   read-only
    STATUS       current
    DESCRIPTION
        "Cisco UCS firmware:Image:size managed object property"
    ::= { cucsFirmwareImageEntry 22 }

cucsFirmwareImageType OBJECT-TYPE
    SYNTAX       CucsFirmwareType
    MAX-ACCESS   read-only
    STATUS       current
    DESCRIPTION
        "Cisco UCS firmware:Image:type managed object property"
    ::= { cucsFirmwareImageEntry 23 }

cucsFirmwareImageVersion OBJECT-TYPE
    SYNTAX       SnmpAdminString
    MAX-ACCESS   read-only
    STATUS       current
    DESCRIPTION
        "Cisco UCS firmware:Image:version managed object property"
    ::= { cucsFirmwareImageEntry 24 }

cucsFirmwareImageDescr OBJECT-TYPE
    SYNTAX       SnmpAdminString
    MAX-ACCESS   read-only
    STATUS       current
    DESCRIPTION
        "Cisco UCS firmware:Image:descr managed object property"
    ::= { cucsFirmwareImageEntry 25 }

cucsFirmwareImageIntId OBJECT-TYPE
    SYNTAX       SnmpAdminString
    MAX-ACCESS   read-only
    STATUS       current
    DESCRIPTION
        "Cisco UCS firmware:Image:intId managed object property"
    ::= { cucsFirmwareImageEntry 26 }

cucsFirmwareImagePolicyLevel OBJECT-TYPE
    SYNTAX       Gauge32
    MAX-ACCESS   read-only
    STATUS       current
    DESCRIPTION
        "Cisco UCS firmware:Image:policyLevel managed object property"
    ::= { cucsFirmwareImageEntry 27 }

cucsFirmwareImagePolicyOwner OBJECT-TYPE
    SYNTAX       CucsPolicyPolicyOwner
    MAX-ACCESS   read-only
    STATUS       current
    DESCRIPTION
        "Cisco UCS firmware:Image:policyOwner managed object property"
    ::= { cucsFirmwareImageEntry 28 }

cucsFirmwareImageFsmTable OBJECT-TYPE
    SYNTAX           SEQUENCE OF CucsFirmwareImageFsmEntry
    MAX-ACCESS       not-accessible
    STATUS           current
    DESCRIPTION
        "Cisco UCS firmware:ImageFsm managed object table"
    ::= { cucsFirmwareObjects 36 }

cucsFirmwareImageFsmEntry OBJECT-TYPE
    SYNTAX           CucsFirmwareImageFsmEntry
    MAX-ACCESS       not-accessible
    STATUS           current
    DESCRIPTION
        "Entry for the cucsFirmwareImageFsmTable table."
    INDEX { cucsFirmwareImageFsmInstanceId }
    ::= { cucsFirmwareImageFsmTable 1 }

CucsFirmwareImageFsmEntry ::= SEQUENCE {
    cucsFirmwareImageFsmInstanceId                                   CucsManagedObjectId,
    cucsFirmwareImageFsmDn                                           CucsManagedObjectDn,
    cucsFirmwareImageFsmRn                                           SnmpAdminString,
    cucsFirmwareImageFsmCompletionTime                               DateAndTime,
    cucsFirmwareImageFsmCurrentFsm                                   CucsFirmwareImageFsmCurrentFsm,
    cucsFirmwareImageFsmDescrData                                    SnmpAdminString,
    cucsFirmwareImageFsmFsmStatus                                    CucsFsmFsmStageStatus,
    cucsFirmwareImageFsmProgress                                     Gauge32,
    cucsFirmwareImageFsmRmtErrCode                                   Gauge32,
    cucsFirmwareImageFsmRmtErrDescr                                  SnmpAdminString,
    cucsFirmwareImageFsmRmtRslt                                      CucsConditionRemoteInvRslt
}

cucsFirmwareImageFsmInstanceId OBJECT-TYPE
    SYNTAX       CucsManagedObjectId
    MAX-ACCESS   not-accessible
    STATUS       current
    DESCRIPTION
        "Instance identifier of the managed object."
    ::= { cucsFirmwareImageFsmEntry 1 }

cucsFirmwareImageFsmDn OBJECT-TYPE
    SYNTAX       CucsManagedObjectDn
    MAX-ACCESS   read-only
    STATUS       current
    DESCRIPTION
        "Cisco UCS firmware:ImageFsm:dn managed object property"
    ::= { cucsFirmwareImageFsmEntry 2 }

cucsFirmwareImageFsmRn OBJECT-TYPE
    SYNTAX       SnmpAdminString
    MAX-ACCESS   read-only
    STATUS       current
    DESCRIPTION
        "Cisco UCS firmware:ImageFsm:rn managed object property"
    ::= { cucsFirmwareImageFsmEntry 3 }

cucsFirmwareImageFsmCompletionTime OBJECT-TYPE
    SYNTAX       DateAndTime
    MAX-ACCESS   read-only
    STATUS       current
    DESCRIPTION
        "Cisco UCS firmware:ImageFsm:completionTime managed
        object property"
    ::= { cucsFirmwareImageFsmEntry 4 }

cucsFirmwareImageFsmCurrentFsm OBJECT-TYPE
    SYNTAX       CucsFirmwareImageFsmCurrentFsm
    MAX-ACCESS   read-only
    STATUS       current
    DESCRIPTION
        "Cisco UCS firmware:ImageFsm:currentFsm managed object property"
    ::= { cucsFirmwareImageFsmEntry 5 }

cucsFirmwareImageFsmDescrData OBJECT-TYPE
    SYNTAX       SnmpAdminString
    MAX-ACCESS   read-only
    STATUS       current
    DESCRIPTION
        "Cisco UCS firmware:ImageFsm:descr managed object property"
    ::= { cucsFirmwareImageFsmEntry 6 }

cucsFirmwareImageFsmFsmStatus OBJECT-TYPE
    SYNTAX       CucsFsmFsmStageStatus
    MAX-ACCESS   read-only
    STATUS       current
    DESCRIPTION
        "Cisco UCS firmware:ImageFsm:fsmStatus managed object property"
    ::= { cucsFirmwareImageFsmEntry 7 }

cucsFirmwareImageFsmProgress OBJECT-TYPE
    SYNTAX       Gauge32
    MAX-ACCESS   read-only
    STATUS       current
    DESCRIPTION
        "Cisco UCS firmware:ImageFsm:progress managed object property"
    ::= { cucsFirmwareImageFsmEntry 8 }

cucsFirmwareImageFsmRmtErrCode OBJECT-TYPE
    SYNTAX       Gauge32
    MAX-ACCESS   read-only
    STATUS       current
    DESCRIPTION
        "Cisco UCS firmware:ImageFsm:rmtErrCode managed object property"
    ::= { cucsFirmwareImageFsmEntry 9 }

cucsFirmwareImageFsmRmtErrDescr OBJECT-TYPE
    SYNTAX       SnmpAdminString
    MAX-ACCESS   read-only
    STATUS       current
    DESCRIPTION
        "Cisco UCS firmware:ImageFsm:rmtErrDescr managed object property"
    ::= { cucsFirmwareImageFsmEntry 10 }

cucsFirmwareImageFsmRmtRslt OBJECT-TYPE
    SYNTAX       CucsConditionRemoteInvRslt
    MAX-ACCESS   read-only
    STATUS       current
    DESCRIPTION
        "Cisco UCS firmware:ImageFsm:rmtRslt managed object property"
    ::= { cucsFirmwareImageFsmEntry 11 }

cucsFirmwareImageFsmStageTable OBJECT-TYPE
    SYNTAX           SEQUENCE OF CucsFirmwareImageFsmStageEntry
    MAX-ACCESS       not-accessible
    STATUS           current
    DESCRIPTION
        "Cisco UCS firmware:ImageFsmStage managed object table"
    ::= { cucsFirmwareObjects 37 }

cucsFirmwareImageFsmStageEntry OBJECT-TYPE
    SYNTAX           CucsFirmwareImageFsmStageEntry
    MAX-ACCESS       not-accessible
    STATUS           current
    DESCRIPTION
        "Entry for the cucsFirmwareImageFsmStageTable table."
    INDEX { cucsFirmwareImageFsmStageInstanceId }
    ::= { cucsFirmwareImageFsmStageTable 1 }

CucsFirmwareImageFsmStageEntry ::= SEQUENCE {
    cucsFirmwareImageFsmStageInstanceId                              CucsManagedObjectId,
    cucsFirmwareImageFsmStageDn                                      CucsManagedObjectDn,
    cucsFirmwareImageFsmStageRn                                      SnmpAdminString,
    cucsFirmwareImageFsmStageDescrData                               SnmpAdminString,
    cucsFirmwareImageFsmStageLastUpdateTime                          DateAndTime,
    cucsFirmwareImageFsmStageName                                    CucsFirmwareImageFsmStageName,
    cucsFirmwareImageFsmStageOrder                                   Gauge32,
    cucsFirmwareImageFsmStageRetry                                   Gauge32,
    cucsFirmwareImageFsmStageStageStatus                             CucsFsmFsmStageStatus
}

cucsFirmwareImageFsmStageInstanceId OBJECT-TYPE
    SYNTAX       CucsManagedObjectId
    MAX-ACCESS   not-accessible
    STATUS       current
    DESCRIPTION
        "Instance identifier of the managed object."
    ::= { cucsFirmwareImageFsmStageEntry 1 }

cucsFirmwareImageFsmStageDn OBJECT-TYPE
    SYNTAX       CucsManagedObjectDn
    MAX-ACCESS   read-only
    STATUS       current
    DESCRIPTION
        "Cisco UCS firmware:ImageFsmStage:dn managed object property"
    ::= { cucsFirmwareImageFsmStageEntry 2 }

cucsFirmwareImageFsmStageRn OBJECT-TYPE
    SYNTAX       SnmpAdminString
    MAX-ACCESS   read-only
    STATUS       current
    DESCRIPTION
        "Cisco UCS firmware:ImageFsmStage:rn managed object property"
    ::= { cucsFirmwareImageFsmStageEntry 3 }

cucsFirmwareImageFsmStageDescrData OBJECT-TYPE
    SYNTAX       SnmpAdminString
    MAX-ACCESS   read-only
    STATUS       current
    DESCRIPTION
        "Cisco UCS firmware:ImageFsmStage:descr managed object property"
    ::= { cucsFirmwareImageFsmStageEntry 4 }

cucsFirmwareImageFsmStageLastUpdateTime OBJECT-TYPE
    SYNTAX       DateAndTime
    MAX-ACCESS   read-only
    STATUS       current
    DESCRIPTION
        "Cisco UCS firmware:ImageFsmStage:lastUpdateTime
        managed object property"
    ::= { cucsFirmwareImageFsmStageEntry 5 }

cucsFirmwareImageFsmStageName OBJECT-TYPE
    SYNTAX       CucsFirmwareImageFsmStageName
    MAX-ACCESS   read-only
    STATUS       current
    DESCRIPTION
        "Cisco UCS firmware:ImageFsmStage:name managed object property"
    ::= { cucsFirmwareImageFsmStageEntry 6 }

cucsFirmwareImageFsmStageOrder OBJECT-TYPE
    SYNTAX       Gauge32
    MAX-ACCESS   read-only
    STATUS       current
    DESCRIPTION
        "Cisco UCS firmware:ImageFsmStage:order managed object property"
    ::= { cucsFirmwareImageFsmStageEntry 7 }

cucsFirmwareImageFsmStageRetry OBJECT-TYPE
    SYNTAX       Gauge32
    MAX-ACCESS   read-only
    STATUS       current
    DESCRIPTION
        "Cisco UCS firmware:ImageFsmStage:retry managed object property"
    ::= { cucsFirmwareImageFsmStageEntry 8 }

cucsFirmwareImageFsmStageStageStatus OBJECT-TYPE
    SYNTAX       CucsFsmFsmStageStatus
    MAX-ACCESS   read-only
    STATUS       current
    DESCRIPTION
        "Cisco UCS firmware:ImageFsmStage:stageStatus managed
        object property"
    ::= { cucsFirmwareImageFsmStageEntry 9 }

cucsFirmwareImageFsmTaskTable OBJECT-TYPE
    SYNTAX           SEQUENCE OF CucsFirmwareImageFsmTaskEntry
    MAX-ACCESS       not-accessible
    STATUS           current
    DESCRIPTION
        "Cisco UCS firmware:ImageFsmTask managed object table"
    ::= { cucsFirmwareObjects 15 }

cucsFirmwareImageFsmTaskEntry OBJECT-TYPE
    SYNTAX           CucsFirmwareImageFsmTaskEntry
    MAX-ACCESS       not-accessible
    STATUS           current
    DESCRIPTION
        "Entry for the cucsFirmwareImageFsmTaskTable table."
    INDEX { cucsFirmwareImageFsmTaskInstanceId }
    ::= { cucsFirmwareImageFsmTaskTable 1 }

CucsFirmwareImageFsmTaskEntry ::= SEQUENCE {
    cucsFirmwareImageFsmTaskInstanceId                               CucsManagedObjectId,
    cucsFirmwareImageFsmTaskDn                                       CucsManagedObjectDn,
    cucsFirmwareImageFsmTaskRn                                       SnmpAdminString,
    cucsFirmwareImageFsmTaskCompletion                               CucsFsmCompletion,
    cucsFirmwareImageFsmTaskFlags                                    CucsFsmFlags,
    cucsFirmwareImageFsmTaskItem                                     CucsFirmwareImageFsmTaskItem,
    cucsFirmwareImageFsmTaskSeqId                                    Gauge32
}

cucsFirmwareImageFsmTaskInstanceId OBJECT-TYPE
    SYNTAX       CucsManagedObjectId
    MAX-ACCESS   not-accessible
    STATUS       current
    DESCRIPTION
        "Instance identifier of the managed object."
    ::= { cucsFirmwareImageFsmTaskEntry 1 }

cucsFirmwareImageFsmTaskDn OBJECT-TYPE
    SYNTAX       CucsManagedObjectDn
    MAX-ACCESS   read-only
    STATUS       current
    DESCRIPTION
        "Cisco UCS firmware:ImageFsmTask:dn managed object property"
    ::= { cucsFirmwareImageFsmTaskEntry 2 }

cucsFirmwareImageFsmTaskRn OBJECT-TYPE
    SYNTAX       SnmpAdminString
    MAX-ACCESS   read-only
    STATUS       current
    DESCRIPTION
        "Cisco UCS firmware:ImageFsmTask:rn managed object property"
    ::= { cucsFirmwareImageFsmTaskEntry 3 }

cucsFirmwareImageFsmTaskCompletion OBJECT-TYPE
    SYNTAX       CucsFsmCompletion
    MAX-ACCESS   read-only
    STATUS       current
    DESCRIPTION
        "Cisco UCS firmware:ImageFsmTask:completion managed
        object property"
    ::= { cucsFirmwareImageFsmTaskEntry 4 }

cucsFirmwareImageFsmTaskFlags OBJECT-TYPE
    SYNTAX       CucsFsmFlags
    MAX-ACCESS   read-only
    STATUS       current
    DESCRIPTION
        "Cisco UCS firmware:ImageFsmTask:flags managed object property"
    ::= { cucsFirmwareImageFsmTaskEntry 5 }

cucsFirmwareImageFsmTaskItem OBJECT-TYPE
    SYNTAX       CucsFirmwareImageFsmTaskItem
    MAX-ACCESS   read-only
    STATUS       current
    DESCRIPTION
        "Cisco UCS firmware:ImageFsmTask:item managed object property"
    ::= { cucsFirmwareImageFsmTaskEntry 6 }

cucsFirmwareImageFsmTaskSeqId OBJECT-TYPE
    SYNTAX       Gauge32
    MAX-ACCESS   read-only
    STATUS       current
    DESCRIPTION
        "Cisco UCS firmware:ImageFsmTask:seqId managed object property"
    ::= { cucsFirmwareImageFsmTaskEntry 7 }

cucsFirmwareImageLockTable OBJECT-TYPE
    SYNTAX           SEQUENCE OF CucsFirmwareImageLockEntry
    MAX-ACCESS       not-accessible
    STATUS           current
    DESCRIPTION
        "Cisco UCS firmware:ImageLock managed object table"
    ::= { cucsFirmwareObjects 51 }

cucsFirmwareImageLockEntry OBJECT-TYPE
    SYNTAX           CucsFirmwareImageLockEntry
    MAX-ACCESS       not-accessible
    STATUS           current
    DESCRIPTION
        "Entry for the cucsFirmwareImageLockTable table."
    INDEX { cucsFirmwareImageLockInstanceId }
    ::= { cucsFirmwareImageLockTable 1 }

CucsFirmwareImageLockEntry ::= SEQUENCE {
    cucsFirmwareImageLockInstanceId                                  CucsManagedObjectId,
    cucsFirmwareImageLockDn                                          CucsManagedObjectDn,
    cucsFirmwareImageLockRn                                          SnmpAdminString,
    cucsFirmwareImageLockImageNameDn                                 SnmpAdminString,
    cucsFirmwareImageLockName                                        SnmpAdminString
}

cucsFirmwareImageLockInstanceId OBJECT-TYPE
    SYNTAX       CucsManagedObjectId
    MAX-ACCESS   not-accessible
    STATUS       current
    DESCRIPTION
        "Instance identifier of the managed object."
    ::= { cucsFirmwareImageLockEntry 1 }

cucsFirmwareImageLockDn OBJECT-TYPE
    SYNTAX       CucsManagedObjectDn
    MAX-ACCESS   read-only
    STATUS       current
    DESCRIPTION
        "Cisco UCS firmware:ImageLock:dn managed object property"
    ::= { cucsFirmwareImageLockEntry 2 }

cucsFirmwareImageLockRn OBJECT-TYPE
    SYNTAX       SnmpAdminString
    MAX-ACCESS   read-only
    STATUS       current
    DESCRIPTION
        "Cisco UCS firmware:ImageLock:rn managed object property"
    ::= { cucsFirmwareImageLockEntry 3 }

cucsFirmwareImageLockImageNameDn OBJECT-TYPE
    SYNTAX       SnmpAdminString
    MAX-ACCESS   read-only
    STATUS       current
    DESCRIPTION
        "Cisco UCS firmware:ImageLock:ImageNameDn managed object property"
    ::= { cucsFirmwareImageLockEntry 4 }

cucsFirmwareImageLockName OBJECT-TYPE
    SYNTAX       SnmpAdminString
    MAX-ACCESS   read-only
    STATUS       current
    DESCRIPTION
        "Cisco UCS firmware:ImageLock:name managed object property"
    ::= { cucsFirmwareImageLockEntry 5 }

cucsFirmwareInfraTable OBJECT-TYPE
    SYNTAX           SEQUENCE OF CucsFirmwareInfraEntry
    MAX-ACCESS       not-accessible
    STATUS           current
    DESCRIPTION
        "Cisco UCS firmware:Infra managed object table"
    ::= { cucsFirmwareObjects 38 }

cucsFirmwareInfraEntry OBJECT-TYPE
    SYNTAX           CucsFirmwareInfraEntry
    MAX-ACCESS       not-accessible
    STATUS           current
    DESCRIPTION
        "Entry for the cucsFirmwareInfraTable table."
    INDEX { cucsFirmwareInfraInstanceId }
    ::= { cucsFirmwareInfraTable 1 }

CucsFirmwareInfraEntry ::= SEQUENCE {
    cucsFirmwareInfraInstanceId                                      CucsManagedObjectId,
    cucsFirmwareInfraDn                                              CucsManagedObjectDn,
    cucsFirmwareInfraRn                                              SnmpAdminString,
    cucsFirmwareInfraAdminState                                      CucsTrigAdminState,
    cucsFirmwareInfraAutoDelete                                      TruthValue,
    cucsFirmwareInfraDescr                                           SnmpAdminString,
    cucsFirmwareInfraIgnoreCap                                       TruthValue,
    cucsFirmwareInfraIntId                                           SnmpAdminString,
    cucsFirmwareInfraName                                            SnmpAdminString,
    cucsFirmwareInfraOperScheduler                                   SnmpAdminString,
    cucsFirmwareInfraOperState                                       CucsTrigTrigOperState,
    cucsFirmwareInfraOperVersion                                     SnmpAdminString,
    cucsFirmwareInfraPolicyLevel                                     Gauge32,
    cucsFirmwareInfraPolicyOwner                                     CucsPolicyPolicyOwner,
    cucsFirmwareInfraScheduler                                       SnmpAdminString
}

cucsFirmwareInfraInstanceId OBJECT-TYPE
    SYNTAX       CucsManagedObjectId
    MAX-ACCESS   not-accessible
    STATUS       current
    DESCRIPTION
        "Instance identifier of the managed object."
    ::= { cucsFirmwareInfraEntry 1 }

cucsFirmwareInfraDn OBJECT-TYPE
    SYNTAX       CucsManagedObjectDn
    MAX-ACCESS   read-only
    STATUS       current
    DESCRIPTION
        "Cisco UCS firmware:Infra:dn managed object property"
    ::= { cucsFirmwareInfraEntry 2 }

cucsFirmwareInfraRn OBJECT-TYPE
    SYNTAX       SnmpAdminString
    MAX-ACCESS   read-only
    STATUS       current
    DESCRIPTION
        "Cisco UCS firmware:Infra:rn managed object property"
    ::= { cucsFirmwareInfraEntry 3 }

cucsFirmwareInfraAdminState OBJECT-TYPE
    SYNTAX       CucsTrigAdminState
    MAX-ACCESS   read-only
    STATUS       current
    DESCRIPTION
        "Cisco UCS firmware:Infra:adminState managed object property"
    ::= { cucsFirmwareInfraEntry 4 }

cucsFirmwareInfraAutoDelete OBJECT-TYPE
    SYNTAX       TruthValue
    MAX-ACCESS   read-only
    STATUS       current
    DESCRIPTION
        "Cisco UCS firmware:Infra:autoDelete managed object property"
    ::= { cucsFirmwareInfraEntry 5 }

cucsFirmwareInfraDescr OBJECT-TYPE
    SYNTAX       SnmpAdminString
    MAX-ACCESS   read-only
    STATUS       current
    DESCRIPTION
        "Cisco UCS firmware:Infra:descr managed object property"
    ::= { cucsFirmwareInfraEntry 6 }

cucsFirmwareInfraIgnoreCap OBJECT-TYPE
    SYNTAX       TruthValue
    MAX-ACCESS   read-only
    STATUS       current
    DESCRIPTION
        "Cisco UCS firmware:Infra:ignoreCap managed object property"
    ::= { cucsFirmwareInfraEntry 7 }

cucsFirmwareInfraIntId OBJECT-TYPE
    SYNTAX       SnmpAdminString
    MAX-ACCESS   read-only
    STATUS       current
    DESCRIPTION
        "Cisco UCS firmware:Infra:intId managed object property"
    ::= { cucsFirmwareInfraEntry 8 }

cucsFirmwareInfraName OBJECT-TYPE
    SYNTAX       SnmpAdminString
    MAX-ACCESS   read-only
    STATUS       current
    DESCRIPTION
        "Cisco UCS firmware:Infra:name managed object property"
    ::= { cucsFirmwareInfraEntry 9 }

cucsFirmwareInfraOperScheduler OBJECT-TYPE
    SYNTAX       SnmpAdminString
    MAX-ACCESS   read-only
    STATUS       current
    DESCRIPTION
        "Cisco UCS firmware:Infra:operScheduler managed object property"
    ::= { cucsFirmwareInfraEntry 10 }

cucsFirmwareInfraOperState OBJECT-TYPE
    SYNTAX       CucsTrigTrigOperState
    MAX-ACCESS   read-only
    STATUS       current
    DESCRIPTION
        "Cisco UCS firmware:Infra:operState managed object property"
    ::= { cucsFirmwareInfraEntry 11 }

cucsFirmwareInfraOperVersion OBJECT-TYPE
    SYNTAX       SnmpAdminString
    MAX-ACCESS   read-only
    STATUS       current
    DESCRIPTION
        "Cisco UCS firmware:Infra:operVersion managed object property"
    ::= { cucsFirmwareInfraEntry 12 }

cucsFirmwareInfraPolicyLevel OBJECT-TYPE
    SYNTAX       Gauge32
    MAX-ACCESS   read-only
    STATUS       current
    DESCRIPTION
        "Cisco UCS firmware:Infra:policyLevel managed object property"
    ::= { cucsFirmwareInfraEntry 13 }

cucsFirmwareInfraPolicyOwner OBJECT-TYPE
    SYNTAX       CucsPolicyPolicyOwner
    MAX-ACCESS   read-only
    STATUS       current
    DESCRIPTION
        "Cisco UCS firmware:Infra:policyOwner managed object property"
    ::= { cucsFirmwareInfraEntry 14 }

cucsFirmwareInfraScheduler OBJECT-TYPE
    SYNTAX       SnmpAdminString
    MAX-ACCESS   read-only
    STATUS       current
    DESCRIPTION
        "Cisco UCS firmware:Infra:scheduler managed object property"
    ::= { cucsFirmwareInfraEntry 15 }

cucsFirmwareInfraPackTable OBJECT-TYPE
    SYNTAX           SEQUENCE OF CucsFirmwareInfraPackEntry
    MAX-ACCESS       not-accessible
    STATUS           current
    DESCRIPTION
        "Cisco UCS firmware:InfraPack managed object table"
    ::= { cucsFirmwareObjects 39 }

cucsFirmwareInfraPackEntry OBJECT-TYPE
    SYNTAX           CucsFirmwareInfraPackEntry
    MAX-ACCESS       not-accessible
    STATUS           current
    DESCRIPTION
        "Entry for the cucsFirmwareInfraPackTable table."
    INDEX { cucsFirmwareInfraPackInstanceId }
    ::= { cucsFirmwareInfraPackTable 1 }

CucsFirmwareInfraPackEntry ::= SEQUENCE {
    cucsFirmwareInfraPackInstanceId                                  CucsManagedObjectId,
    cucsFirmwareInfraPackDn                                          CucsManagedObjectDn,
    cucsFirmwareInfraPackRn                                          SnmpAdminString,
    cucsFirmwareInfraPackDescr                                       SnmpAdminString,
    cucsFirmwareInfraPackForceDeploy                                 TruthValue,
    cucsFirmwareInfraPackInfraBundleName                             SnmpAdminString,
    cucsFirmwareInfraPackInfraBundleVersion                          SnmpAdminString,
    cucsFirmwareInfraPackIntId                                       SnmpAdminString,
    cucsFirmwareInfraPackMode                                        CucsFirmwarePackMode,
    cucsFirmwareInfraPackName                                        SnmpAdminString,
    cucsFirmwareInfraPackPolicyLevel                                 Gauge32,
    cucsFirmwareInfraPackPolicyOwner                                 CucsPolicyPolicyOwner,
    cucsFirmwareInfraPackStageSize                                   Gauge32,
    cucsFirmwareInfraPackUpdateTrigger                               DateAndTime
}

cucsFirmwareInfraPackInstanceId OBJECT-TYPE
    SYNTAX       CucsManagedObjectId
    MAX-ACCESS   not-accessible
    STATUS       current
    DESCRIPTION
        "Instance identifier of the managed object."
    ::= { cucsFirmwareInfraPackEntry 1 }

cucsFirmwareInfraPackDn OBJECT-TYPE
    SYNTAX       CucsManagedObjectDn
    MAX-ACCESS   read-only
    STATUS       current
    DESCRIPTION
        "Cisco UCS firmware:InfraPack:dn managed object property"
    ::= { cucsFirmwareInfraPackEntry 2 }

cucsFirmwareInfraPackRn OBJECT-TYPE
    SYNTAX       SnmpAdminString
    MAX-ACCESS   read-only
    STATUS       current
    DESCRIPTION
        "Cisco UCS firmware:InfraPack:rn managed object property"
    ::= { cucsFirmwareInfraPackEntry 3 }

cucsFirmwareInfraPackDescr OBJECT-TYPE
    SYNTAX       SnmpAdminString
    MAX-ACCESS   read-only
    STATUS       current
    DESCRIPTION
        "Cisco UCS firmware:InfraPack:descr managed object property"
    ::= { cucsFirmwareInfraPackEntry 4 }

cucsFirmwareInfraPackForceDeploy OBJECT-TYPE
    SYNTAX       TruthValue
    MAX-ACCESS   read-only
    STATUS       current
    DESCRIPTION
        "Cisco UCS firmware:InfraPack:forceDeploy managed object property"
    ::= { cucsFirmwareInfraPackEntry 5 }

cucsFirmwareInfraPackInfraBundleName OBJECT-TYPE
    SYNTAX       SnmpAdminString
    MAX-ACCESS   read-only
    STATUS       current
    DESCRIPTION
        "Cisco UCS firmware:InfraPack:infraBundleName managed
        object property"
    ::= { cucsFirmwareInfraPackEntry 6 }

cucsFirmwareInfraPackInfraBundleVersion OBJECT-TYPE
    SYNTAX       SnmpAdminString
    MAX-ACCESS   read-only
    STATUS       current
    DESCRIPTION
        "Cisco UCS firmware:InfraPack:infraBundleVersion
        managed object property"
    ::= { cucsFirmwareInfraPackEntry 7 }

cucsFirmwareInfraPackIntId OBJECT-TYPE
    SYNTAX       SnmpAdminString
    MAX-ACCESS   read-only
    STATUS       current
    DESCRIPTION
        "Cisco UCS firmware:InfraPack:intId managed object property"
    ::= { cucsFirmwareInfraPackEntry 8 }

cucsFirmwareInfraPackMode OBJECT-TYPE
    SYNTAX       CucsFirmwarePackMode
    MAX-ACCESS   read-only
    STATUS       current
    DESCRIPTION
        "Cisco UCS firmware:InfraPack:mode managed object property"
    ::= { cucsFirmwareInfraPackEntry 9 }

cucsFirmwareInfraPackName OBJECT-TYPE
    SYNTAX       SnmpAdminString
    MAX-ACCESS   read-only
    STATUS       current
    DESCRIPTION
        "Cisco UCS firmware:InfraPack:name managed object property"
    ::= { cucsFirmwareInfraPackEntry 10 }

cucsFirmwareInfraPackPolicyLevel OBJECT-TYPE
    SYNTAX       Gauge32
    MAX-ACCESS   read-only
    STATUS       current
    DESCRIPTION
        "Cisco UCS firmware:InfraPack:policyLevel managed object property"
    ::= { cucsFirmwareInfraPackEntry 11 }

cucsFirmwareInfraPackPolicyOwner OBJECT-TYPE
    SYNTAX       CucsPolicyPolicyOwner
    MAX-ACCESS   read-only
    STATUS       current
    DESCRIPTION
        "Cisco UCS firmware:InfraPack:policyOwner managed object property"
    ::= { cucsFirmwareInfraPackEntry 12 }

cucsFirmwareInfraPackStageSize OBJECT-TYPE
    SYNTAX       Gauge32
    MAX-ACCESS   read-only
    STATUS       current
    DESCRIPTION
        "Cisco UCS firmware:InfraPack:stageSize managed object property"
    ::= { cucsFirmwareInfraPackEntry 13 }

cucsFirmwareInfraPackUpdateTrigger OBJECT-TYPE
    SYNTAX       DateAndTime
    MAX-ACCESS   read-only
    STATUS       current
    DESCRIPTION
        "Cisco UCS firmware:InfraPack:updateTrigger managed
        object property"
    ::= { cucsFirmwareInfraPackEntry 14 }

cucsFirmwareInstallImpactTable OBJECT-TYPE
    SYNTAX           SEQUENCE OF CucsFirmwareInstallImpactEntry
    MAX-ACCESS       not-accessible
    STATUS           current
    DESCRIPTION
        "Cisco UCS firmware:InstallImpact managed object table"
    ::= { cucsFirmwareObjects 40 }

cucsFirmwareInstallImpactEntry OBJECT-TYPE
    SYNTAX           CucsFirmwareInstallImpactEntry
    MAX-ACCESS       not-accessible
    STATUS           current
    DESCRIPTION
        "Entry for the cucsFirmwareInstallImpactTable table."
    INDEX { cucsFirmwareInstallImpactInstanceId }
    ::= { cucsFirmwareInstallImpactTable 1 }

CucsFirmwareInstallImpactEntry ::= SEQUENCE {
    cucsFirmwareInstallImpactInstanceId                              CucsManagedObjectId,
    cucsFirmwareInstallImpactDn                                      CucsManagedObjectDn,
    cucsFirmwareInstallImpactRn                                      SnmpAdminString,
    cucsFirmwareInstallImpactDescr                                   SnmpAdminString,
    cucsFirmwareInstallImpactKeyDn                                   SnmpAdminString,
    cucsFirmwareInstallImpactMaintPolicyDn                           SnmpAdminString,
    cucsFirmwareInstallImpactRebootPolicy                            SnmpAdminString,
    cucsFirmwareInstallImpactSubject                                 CucsFirmwareEquipmentType,
    cucsFirmwareInstallImpactType                                    CucsFirmwareImpactType
}

cucsFirmwareInstallImpactInstanceId OBJECT-TYPE
    SYNTAX       CucsManagedObjectId
    MAX-ACCESS   not-accessible
    STATUS       current
    DESCRIPTION
        "Instance identifier of the managed object."
    ::= { cucsFirmwareInstallImpactEntry 1 }

cucsFirmwareInstallImpactDn OBJECT-TYPE
    SYNTAX       CucsManagedObjectDn
    MAX-ACCESS   read-only
    STATUS       current
    DESCRIPTION
        "Cisco UCS firmware:InstallImpact:dn managed object property"
    ::= { cucsFirmwareInstallImpactEntry 2 }

cucsFirmwareInstallImpactRn OBJECT-TYPE
    SYNTAX       SnmpAdminString
    MAX-ACCESS   read-only
    STATUS       current
    DESCRIPTION
        "Cisco UCS firmware:InstallImpact:rn managed object property"
    ::= { cucsFirmwareInstallImpactEntry 3 }

cucsFirmwareInstallImpactDescr OBJECT-TYPE
    SYNTAX       SnmpAdminString
    MAX-ACCESS   read-only
    STATUS       current
    DESCRIPTION
        "Cisco UCS firmware:InstallImpact:descr managed object property"
    ::= { cucsFirmwareInstallImpactEntry 4 }

cucsFirmwareInstallImpactKeyDn OBJECT-TYPE
    SYNTAX       SnmpAdminString
    MAX-ACCESS   read-only
    STATUS       current
    DESCRIPTION
        "Cisco UCS firmware:InstallImpact:keyDn managed object property"
    ::= { cucsFirmwareInstallImpactEntry 5 }

cucsFirmwareInstallImpactMaintPolicyDn OBJECT-TYPE
    SYNTAX       SnmpAdminString
    MAX-ACCESS   read-only
    STATUS       current
    DESCRIPTION
        "Cisco UCS firmware:InstallImpact:maintPolicyDn
        managed object property"
    ::= { cucsFirmwareInstallImpactEntry 6 }

cucsFirmwareInstallImpactRebootPolicy OBJECT-TYPE
    SYNTAX       SnmpAdminString
    MAX-ACCESS   read-only
    STATUS       current
    DESCRIPTION
        "Cisco UCS firmware:InstallImpact:rebootPolicy
        managed object property"
    ::= { cucsFirmwareInstallImpactEntry 7 }

cucsFirmwareInstallImpactSubject OBJECT-TYPE
    SYNTAX       CucsFirmwareEquipmentType
    MAX-ACCESS   read-only
    STATUS       current
    DESCRIPTION
        "Cisco UCS firmware:InstallImpact:subject managed object property"
    ::= { cucsFirmwareInstallImpactEntry 8 }

cucsFirmwareInstallImpactType OBJECT-TYPE
    SYNTAX       CucsFirmwareImpactType
    MAX-ACCESS   read-only
    STATUS       current
    DESCRIPTION
        "Cisco UCS firmware:InstallImpact:type managed object property"
    ::= { cucsFirmwareInstallImpactEntry 9 }

cucsFirmwareInstallableTable OBJECT-TYPE
    SYNTAX           SEQUENCE OF CucsFirmwareInstallableEntry
    MAX-ACCESS       not-accessible
    STATUS           current
    DESCRIPTION
        "Cisco UCS firmware:Installable managed object table"
    ::= { cucsFirmwareObjects 16 }

cucsFirmwareInstallableEntry OBJECT-TYPE
    SYNTAX           CucsFirmwareInstallableEntry
    MAX-ACCESS       not-accessible
    STATUS           current
    DESCRIPTION
        "Entry for the cucsFirmwareInstallableTable table."
    INDEX { cucsFirmwareInstallableInstanceId }
    ::= { cucsFirmwareInstallableTable 1 }

CucsFirmwareInstallableEntry ::= SEQUENCE {
    cucsFirmwareInstallableInstanceId                                CucsManagedObjectId,
    cucsFirmwareInstallableDn                                        CucsManagedObjectDn,
    cucsFirmwareInstallableRn                                        SnmpAdminString,
    cucsFirmwareInstallableChecksum                                  SnmpAdminString,
    cucsFirmwareInstallableInProgress                                Gauge32,
    cucsFirmwareInstallableIsoname                                   SnmpAdminString,
    cucsFirmwareInstallableLocation                                  SnmpAdminString,
    cucsFirmwareInstallableModel                                     SnmpAdminString,
    cucsFirmwareInstallableName                                      SnmpAdminString,
    cucsFirmwareInstallableSize                                      Gauge32,
    cucsFirmwareInstallableType                                      CucsFirmwareType,
    cucsFirmwareInstallableVendor                                    SnmpAdminString,
    cucsFirmwareInstallableVersion                                   SnmpAdminString
}

cucsFirmwareInstallableInstanceId OBJECT-TYPE
    SYNTAX       CucsManagedObjectId
    MAX-ACCESS   not-accessible
    STATUS       current
    DESCRIPTION
        "Instance identifier of the managed object."
    ::= { cucsFirmwareInstallableEntry 1 }

cucsFirmwareInstallableDn OBJECT-TYPE
    SYNTAX       CucsManagedObjectDn
    MAX-ACCESS   read-only
    STATUS       current
    DESCRIPTION
        "Cisco UCS firmware:Installable:dn managed object property"
    ::= { cucsFirmwareInstallableEntry 2 }

cucsFirmwareInstallableRn OBJECT-TYPE
    SYNTAX       SnmpAdminString
    MAX-ACCESS   read-only
    STATUS       current
    DESCRIPTION
        "Cisco UCS firmware:Installable:rn managed object property"
    ::= { cucsFirmwareInstallableEntry 3 }

cucsFirmwareInstallableChecksum OBJECT-TYPE
    SYNTAX       SnmpAdminString
    MAX-ACCESS   read-only
    STATUS       current
    DESCRIPTION
        "Cisco UCS firmware:Installable:checksum managed object property"
    ::= { cucsFirmwareInstallableEntry 4 }

cucsFirmwareInstallableInProgress OBJECT-TYPE
    SYNTAX       Gauge32
    MAX-ACCESS   read-only
    STATUS       current
    DESCRIPTION
        "Cisco UCS firmware:Installable:inProgress managed
        object property"
    ::= { cucsFirmwareInstallableEntry 5 }

cucsFirmwareInstallableIsoname OBJECT-TYPE
    SYNTAX       SnmpAdminString
    MAX-ACCESS   read-only
    STATUS       current
    DESCRIPTION
        "Cisco UCS firmware:Installable:isoname managed object property"
    ::= { cucsFirmwareInstallableEntry 6 }

cucsFirmwareInstallableLocation OBJECT-TYPE
    SYNTAX       SnmpAdminString
    MAX-ACCESS   read-only
    STATUS       current
    DESCRIPTION
        "Cisco UCS firmware:Installable:location managed object property"
    ::= { cucsFirmwareInstallableEntry 7 }

cucsFirmwareInstallableModel OBJECT-TYPE
    SYNTAX       SnmpAdminString
    MAX-ACCESS   read-only
    STATUS       current
    DESCRIPTION
        "Cisco UCS firmware:Installable:model managed object property"
    ::= { cucsFirmwareInstallableEntry 8 }

cucsFirmwareInstallableName OBJECT-TYPE
    SYNTAX       SnmpAdminString
    MAX-ACCESS   read-only
    STATUS       current
    DESCRIPTION
        "Cisco UCS firmware:Installable:name managed object property"
    ::= { cucsFirmwareInstallableEntry 9 }

cucsFirmwareInstallableSize OBJECT-TYPE
    SYNTAX       Gauge32
    MAX-ACCESS   read-only
    STATUS       current
    DESCRIPTION
        "Cisco UCS firmware:Installable:size managed object property"
    ::= { cucsFirmwareInstallableEntry 10 }

cucsFirmwareInstallableType OBJECT-TYPE
    SYNTAX       CucsFirmwareType
    MAX-ACCESS   read-only
    STATUS       current
    DESCRIPTION
        "Cisco UCS firmware:Installable:type managed object property"
    ::= { cucsFirmwareInstallableEntry 11 }

cucsFirmwareInstallableVendor OBJECT-TYPE
    SYNTAX       SnmpAdminString
    MAX-ACCESS   read-only
    STATUS       current
    DESCRIPTION
        "Cisco UCS firmware:Installable:vendor managed object property"
    ::= { cucsFirmwareInstallableEntry 12 }

cucsFirmwareInstallableVersion OBJECT-TYPE
    SYNTAX       SnmpAdminString
    MAX-ACCESS   read-only
    STATUS       current
    DESCRIPTION
        "Cisco UCS firmware:Installable:version managed object property"
    ::= { cucsFirmwareInstallableEntry 13 }

cucsFirmwarePackItemTable OBJECT-TYPE
    SYNTAX           SEQUENCE OF CucsFirmwarePackItemEntry
    MAX-ACCESS       not-accessible
    STATUS           current
    DESCRIPTION
        "Cisco UCS firmware:PackItem managed object table"
    ::= { cucsFirmwareObjects 17 }

cucsFirmwarePackItemEntry OBJECT-TYPE
    SYNTAX           CucsFirmwarePackItemEntry
    MAX-ACCESS       not-accessible
    STATUS           current
    DESCRIPTION
        "Entry for the cucsFirmwarePackItemTable table."
    INDEX { cucsFirmwarePackItemInstanceId }
    ::= { cucsFirmwarePackItemTable 1 }

CucsFirmwarePackItemEntry ::= SEQUENCE {
    cucsFirmwarePackItemInstanceId                                   CucsManagedObjectId,
    cucsFirmwarePackItemDn                                           CucsManagedObjectDn,
    cucsFirmwarePackItemRn                                           SnmpAdminString,
    cucsFirmwarePackItemHwModel                                      SnmpAdminString,
    cucsFirmwarePackItemHwVendor                                     SnmpAdminString,
    cucsFirmwarePackItemPresence                                     CucsFirmwarePackItemPresence,
    cucsFirmwarePackItemType                                         CucsFirmwareItemType,
    cucsFirmwarePackItemVersion                                      SnmpAdminString
}

cucsFirmwarePackItemInstanceId OBJECT-TYPE
    SYNTAX       CucsManagedObjectId
    MAX-ACCESS   not-accessible
    STATUS       current
    DESCRIPTION
        "Instance identifier of the managed object."
    ::= { cucsFirmwarePackItemEntry 1 }

cucsFirmwarePackItemDn OBJECT-TYPE
    SYNTAX       CucsManagedObjectDn
    MAX-ACCESS   read-only
    STATUS       current
    DESCRIPTION
        "Cisco UCS firmware:PackItem:dn managed object property"
    ::= { cucsFirmwarePackItemEntry 2 }

cucsFirmwarePackItemRn OBJECT-TYPE
    SYNTAX       SnmpAdminString
    MAX-ACCESS   read-only
    STATUS       current
    DESCRIPTION
        "Cisco UCS firmware:PackItem:rn managed object property"
    ::= { cucsFirmwarePackItemEntry 3 }

cucsFirmwarePackItemHwModel OBJECT-TYPE
    SYNTAX       SnmpAdminString
    MAX-ACCESS   read-only
    STATUS       current
    DESCRIPTION
        "Cisco UCS firmware:PackItem:hwModel managed object property"
    ::= { cucsFirmwarePackItemEntry 4 }

cucsFirmwarePackItemHwVendor OBJECT-TYPE
    SYNTAX       SnmpAdminString
    MAX-ACCESS   read-only
    STATUS       current
    DESCRIPTION
        "Cisco UCS firmware:PackItem:hwVendor managed object property"
    ::= { cucsFirmwarePackItemEntry 5 }

cucsFirmwarePackItemPresence OBJECT-TYPE
    SYNTAX       CucsFirmwarePackItemPresence
    MAX-ACCESS   read-only
    STATUS       current
    DESCRIPTION
        "Cisco UCS firmware:PackItem:presence managed object property"
    ::= { cucsFirmwarePackItemEntry 6 }

cucsFirmwarePackItemType OBJECT-TYPE
    SYNTAX       CucsFirmwareItemType
    MAX-ACCESS   read-only
    STATUS       current
    DESCRIPTION
        "Cisco UCS firmware:PackItem:type managed object property"
    ::= { cucsFirmwarePackItemEntry 7 }

cucsFirmwarePackItemVersion OBJECT-TYPE
    SYNTAX       SnmpAdminString
    MAX-ACCESS   read-only
    STATUS       current
    DESCRIPTION
        "Cisco UCS firmware:PackItem:version managed object property"
    ::= { cucsFirmwarePackItemEntry 8 }

cucsFirmwareRackTable OBJECT-TYPE
    SYNTAX           SEQUENCE OF CucsFirmwareRackEntry
    MAX-ACCESS       not-accessible
    STATUS           current
    DESCRIPTION
        "Cisco UCS firmware:Rack managed object table"
    ::= { cucsFirmwareObjects 41 }

cucsFirmwareRackEntry OBJECT-TYPE
    SYNTAX           CucsFirmwareRackEntry
    MAX-ACCESS       not-accessible
    STATUS           current
    DESCRIPTION
        "Entry for the cucsFirmwareRackTable table."
    INDEX { cucsFirmwareRackInstanceId }
    ::= { cucsFirmwareRackTable 1 }

CucsFirmwareRackEntry ::= SEQUENCE {
    cucsFirmwareRackInstanceId                                       CucsManagedObjectId,
    cucsFirmwareRackDn                                               CucsManagedObjectDn,
    cucsFirmwareRackRn                                               SnmpAdminString,
    cucsFirmwareRackOperVersion                                      SnmpAdminString
}

cucsFirmwareRackInstanceId OBJECT-TYPE
    SYNTAX       CucsManagedObjectId
    MAX-ACCESS   not-accessible
    STATUS       current
    DESCRIPTION
        "Instance identifier of the managed object."
    ::= { cucsFirmwareRackEntry 1 }

cucsFirmwareRackDn OBJECT-TYPE
    SYNTAX       CucsManagedObjectDn
    MAX-ACCESS   read-only
    STATUS       current
    DESCRIPTION
        "Cisco UCS firmware:Rack:dn managed object property"
    ::= { cucsFirmwareRackEntry 2 }

cucsFirmwareRackRn OBJECT-TYPE
    SYNTAX       SnmpAdminString
    MAX-ACCESS   read-only
    STATUS       current
    DESCRIPTION
        "Cisco UCS firmware:Rack:rn managed object property"
    ::= { cucsFirmwareRackEntry 3 }

cucsFirmwareRackOperVersion OBJECT-TYPE
    SYNTAX       SnmpAdminString
    MAX-ACCESS   read-only
    STATUS       current
    DESCRIPTION
        "Cisco UCS firmware:Rack:operVersion managed object property"
    ::= { cucsFirmwareRackEntry 4 }

cucsFirmwareRunningTable OBJECT-TYPE
    SYNTAX           SEQUENCE OF CucsFirmwareRunningEntry
    MAX-ACCESS       not-accessible
    STATUS           current
    DESCRIPTION
        "Cisco UCS firmware:Running managed object table"
    ::= { cucsFirmwareObjects 18 }

cucsFirmwareRunningEntry OBJECT-TYPE
    SYNTAX           CucsFirmwareRunningEntry
    MAX-ACCESS       not-accessible
    STATUS           current
    DESCRIPTION
        "Entry for the cucsFirmwareRunningTable table."
    INDEX { cucsFirmwareRunningInstanceId }
    ::= { cucsFirmwareRunningTable 1 }

CucsFirmwareRunningEntry ::= SEQUENCE {
    cucsFirmwareRunningInstanceId                                    CucsManagedObjectId,
    cucsFirmwareRunningDn                                            CucsManagedObjectDn,
    cucsFirmwareRunningRn                                            SnmpAdminString,
    cucsFirmwareRunningDeployment                                    CucsFirmwareRunningDeployment,
    cucsFirmwareRunningType                                          CucsFirmwareType,
    cucsFirmwareRunningVersion                                       SnmpAdminString,
    cucsFirmwareRunningPackageVersion                                SnmpAdminString
}

cucsFirmwareRunningInstanceId OBJECT-TYPE
    SYNTAX       CucsManagedObjectId
    MAX-ACCESS   not-accessible
    STATUS       current
    DESCRIPTION
        "Instance identifier of the managed object."
    ::= { cucsFirmwareRunningEntry 1 }

cucsFirmwareRunningDn OBJECT-TYPE
    SYNTAX       CucsManagedObjectDn
    MAX-ACCESS   read-only
    STATUS       current
    DESCRIPTION
        "Cisco UCS firmware:Running:dn managed object property"
    ::= { cucsFirmwareRunningEntry 2 }

cucsFirmwareRunningRn OBJECT-TYPE
    SYNTAX       SnmpAdminString
    MAX-ACCESS   read-only
    STATUS       current
    DESCRIPTION
        "Cisco UCS firmware:Running:rn managed object property"
    ::= { cucsFirmwareRunningEntry 3 }

cucsFirmwareRunningDeployment OBJECT-TYPE
    SYNTAX       CucsFirmwareRunningDeployment
    MAX-ACCESS   read-only
    STATUS       current
    DESCRIPTION
        "Cisco UCS firmware:Running:deployment managed object property"
    ::= { cucsFirmwareRunningEntry 4 }

cucsFirmwareRunningType OBJECT-TYPE
    SYNTAX       CucsFirmwareType
    MAX-ACCESS   read-only
    STATUS       current
    DESCRIPTION
        "Cisco UCS firmware:Running:type managed object property"
    ::= { cucsFirmwareRunningEntry 5 }

cucsFirmwareRunningVersion OBJECT-TYPE
    SYNTAX       SnmpAdminString
    MAX-ACCESS   read-only
    STATUS       current
    DESCRIPTION
        "Cisco UCS firmware:Running:version managed object property"
    ::= { cucsFirmwareRunningEntry 6 }

cucsFirmwareRunningPackageVersion OBJECT-TYPE
    SYNTAX       SnmpAdminString
    MAX-ACCESS   read-only
    STATUS       current
    DESCRIPTION
        "Cisco UCS firmware:Running:packageVersion managed
        object property"
    ::= { cucsFirmwareRunningEntry 7 }

cucsFirmwareSpecTable OBJECT-TYPE
    SYNTAX           SEQUENCE OF CucsFirmwareSpecEntry
    MAX-ACCESS       not-accessible
    STATUS           current
    DESCRIPTION
        "Cisco UCS firmware:Spec managed object table"
    ::= { cucsFirmwareObjects 23 }

cucsFirmwareSpecEntry OBJECT-TYPE
    SYNTAX           CucsFirmwareSpecEntry
    MAX-ACCESS       not-accessible
    STATUS           current
    DESCRIPTION
        "Entry for the cucsFirmwareSpecTable table."
    INDEX { cucsFirmwareSpecInstanceId }
    ::= { cucsFirmwareSpecTable 1 }

CucsFirmwareSpecEntry ::= SEQUENCE {
    cucsFirmwareSpecInstanceId                                       CucsManagedObjectId,
    cucsFirmwareSpecDn                                               CucsManagedObjectDn,
    cucsFirmwareSpecRn                                               SnmpAdminString,
    cucsFirmwareSpecBundleVersion                                    SnmpAdminString,
    cucsFirmwareSpecEthEFIVersion                                    SnmpAdminString,
    cucsFirmwareSpecEthOptionRomVersion                              SnmpAdminString,
    cucsFirmwareSpecFcFWVersion                                      SnmpAdminString,
    cucsFirmwareSpecFcOptionRomVersion                               SnmpAdminString
}

cucsFirmwareSpecInstanceId OBJECT-TYPE
    SYNTAX       CucsManagedObjectId
    MAX-ACCESS   not-accessible
    STATUS       current
    DESCRIPTION
        "Instance identifier of the managed object."
    ::= { cucsFirmwareSpecEntry 1 }

cucsFirmwareSpecDn OBJECT-TYPE
    SYNTAX       CucsManagedObjectDn
    MAX-ACCESS   read-only
    STATUS       current
    DESCRIPTION
        "Cisco UCS firmware:Spec:dn managed object property"
    ::= { cucsFirmwareSpecEntry 2 }

cucsFirmwareSpecRn OBJECT-TYPE
    SYNTAX       SnmpAdminString
    MAX-ACCESS   read-only
    STATUS       current
    DESCRIPTION
        "Cisco UCS firmware:Spec:rn managed object property"
    ::= { cucsFirmwareSpecEntry 3 }

cucsFirmwareSpecBundleVersion OBJECT-TYPE
    SYNTAX       SnmpAdminString
    MAX-ACCESS   read-only
    STATUS       current
    DESCRIPTION
        "Cisco UCS firmware:Spec:bundleVersion managed object property"
    ::= { cucsFirmwareSpecEntry 4 }

cucsFirmwareSpecEthEFIVersion OBJECT-TYPE
    SYNTAX       SnmpAdminString
    MAX-ACCESS   read-only
    STATUS       current
    DESCRIPTION
        "Cisco UCS firmware:Spec:ethEFIVersion managed object property"
    ::= { cucsFirmwareSpecEntry 5 }

cucsFirmwareSpecEthOptionRomVersion OBJECT-TYPE
    SYNTAX       SnmpAdminString
    MAX-ACCESS   read-only
    STATUS       current
    DESCRIPTION
        "Cisco UCS firmware:Spec:ethOptionRomVersion managed
        object property"
    ::= { cucsFirmwareSpecEntry 6 }

cucsFirmwareSpecFcFWVersion OBJECT-TYPE
    SYNTAX       SnmpAdminString
    MAX-ACCESS   read-only
    STATUS       current
    DESCRIPTION
        "Cisco UCS firmware:Spec:fcFWVersion managed object property"
    ::= { cucsFirmwareSpecEntry 7 }

cucsFirmwareSpecFcOptionRomVersion OBJECT-TYPE
    SYNTAX       SnmpAdminString
    MAX-ACCESS   read-only
    STATUS       current
    DESCRIPTION
        "Cisco UCS firmware:Spec:fcOptionRomVersion managed
        object property"
    ::= { cucsFirmwareSpecEntry 8 }

cucsFirmwareStatusTable OBJECT-TYPE
    SYNTAX           SEQUENCE OF CucsFirmwareStatusEntry
    MAX-ACCESS       not-accessible
    STATUS           current
    DESCRIPTION
        "Cisco UCS firmware:Status managed object table"
    ::= { cucsFirmwareObjects 42 }

cucsFirmwareStatusEntry OBJECT-TYPE
    SYNTAX           CucsFirmwareStatusEntry
    MAX-ACCESS       not-accessible
    STATUS           current
    DESCRIPTION
        "Entry for the cucsFirmwareStatusTable table."
    INDEX { cucsFirmwareStatusInstanceId }
    ::= { cucsFirmwareStatusTable 1 }

CucsFirmwareStatusEntry ::= SEQUENCE {
    cucsFirmwareStatusInstanceId                                     CucsManagedObjectId,
    cucsFirmwareStatusDn                                             CucsManagedObjectDn,
    cucsFirmwareStatusRn                                             SnmpAdminString,
    cucsFirmwareStatusOperState                                      CucsFirmwareImageState,
    cucsFirmwareStatusPackageVersion                                 SnmpAdminString,
    cucsFirmwareStatusCimcVersion                                    SnmpAdminString,
    cucsFirmwareStatusFirmwareState                                  CucsFirmwareFirmwareState,
    cucsFirmwareStatusPldVersion                                     SnmpAdminString
}

cucsFirmwareStatusInstanceId OBJECT-TYPE
    SYNTAX       CucsManagedObjectId
    MAX-ACCESS   not-accessible
    STATUS       current
    DESCRIPTION
        "Instance identifier of the managed object."
    ::= { cucsFirmwareStatusEntry 1 }

cucsFirmwareStatusDn OBJECT-TYPE
    SYNTAX       CucsManagedObjectDn
    MAX-ACCESS   read-only
    STATUS       current
    DESCRIPTION
        "Cisco UCS firmware:Status:dn managed object property"
    ::= { cucsFirmwareStatusEntry 2 }

cucsFirmwareStatusRn OBJECT-TYPE
    SYNTAX       SnmpAdminString
    MAX-ACCESS   read-only
    STATUS       current
    DESCRIPTION
        "Cisco UCS firmware:Status:rn managed object property"
    ::= { cucsFirmwareStatusEntry 3 }

cucsFirmwareStatusOperState OBJECT-TYPE
    SYNTAX       CucsFirmwareImageState
    MAX-ACCESS   read-only
    STATUS       current
    DESCRIPTION
        "Cisco UCS firmware:Status:operState managed object property"
    ::= { cucsFirmwareStatusEntry 4 }

cucsFirmwareStatusPackageVersion OBJECT-TYPE
    SYNTAX       SnmpAdminString
    MAX-ACCESS   read-only
    STATUS       current
    DESCRIPTION
        "Cisco UCS firmware:Status:packageVersion managed object property"
    ::= { cucsFirmwareStatusEntry 5 }

cucsFirmwareStatusCimcVersion OBJECT-TYPE
    SYNTAX       SnmpAdminString
    MAX-ACCESS   read-only
    STATUS       current
    DESCRIPTION
        "Cisco UCS firmware:Status:cimcVersion managed object property"
    ::= { cucsFirmwareStatusEntry 6 }

cucsFirmwareStatusFirmwareState OBJECT-TYPE
    SYNTAX       CucsFirmwareFirmwareState
    MAX-ACCESS   read-only
    STATUS       current
    DESCRIPTION
        "Cisco UCS firmware:Status:firmwareState managed object property"
    ::= { cucsFirmwareStatusEntry 7 }

cucsFirmwareStatusPldVersion OBJECT-TYPE
    SYNTAX       SnmpAdminString
    MAX-ACCESS   read-only
    STATUS       current
    DESCRIPTION
        "Cisco UCS firmware:Status:pldVersion managed object property"
    ::= { cucsFirmwareStatusEntry 8 }

cucsFirmwareSystemTable OBJECT-TYPE
    SYNTAX           SEQUENCE OF CucsFirmwareSystemEntry
    MAX-ACCESS       not-accessible
    STATUS           current
    DESCRIPTION
        "Cisco UCS firmware:System managed object table"
    ::= { cucsFirmwareObjects 43 }

cucsFirmwareSystemEntry OBJECT-TYPE
    SYNTAX           CucsFirmwareSystemEntry
    MAX-ACCESS       not-accessible
    STATUS           current
    DESCRIPTION
        "Entry for the cucsFirmwareSystemTable table."
    INDEX { cucsFirmwareSystemInstanceId }
    ::= { cucsFirmwareSystemTable 1 }

CucsFirmwareSystemEntry ::= SEQUENCE {
    cucsFirmwareSystemInstanceId                                     CucsManagedObjectId,
    cucsFirmwareSystemDn                                             CucsManagedObjectDn,
    cucsFirmwareSystemRn                                             SnmpAdminString,
    cucsFirmwareSystemFsmDescr                                       SnmpAdminString,
    cucsFirmwareSystemFsmFlags                                       SnmpAdminString,
    cucsFirmwareSystemFsmPrev                                        SnmpAdminString,
    cucsFirmwareSystemFsmProgr                                       Gauge32,
    cucsFirmwareSystemFsmRmtInvErrCode                               Gauge32,
    cucsFirmwareSystemFsmRmtInvErrDescr                              SnmpAdminString,
    cucsFirmwareSystemFsmRmtInvRslt                                  CucsConditionRemoteInvRslt,
    cucsFirmwareSystemFsmStageDescr                                  SnmpAdminString,
    cucsFirmwareSystemFsmStamp                                       DateAndTime,
    cucsFirmwareSystemFsmStatus                                      SnmpAdminString,
    cucsFirmwareSystemFsmTry                                         Gauge32,
    cucsFirmwareSystemOperState                                      CucsFirmwareInstallState,
    cucsFirmwareSystemState                                          CucsFirmwareFwState
}

cucsFirmwareSystemInstanceId OBJECT-TYPE
    SYNTAX       CucsManagedObjectId
    MAX-ACCESS   not-accessible
    STATUS       current
    DESCRIPTION
        "Instance identifier of the managed object."
    ::= { cucsFirmwareSystemEntry 1 }

cucsFirmwareSystemDn OBJECT-TYPE
    SYNTAX       CucsManagedObjectDn
    MAX-ACCESS   read-only
    STATUS       current
    DESCRIPTION
        "Cisco UCS firmware:System:dn managed object property"
    ::= { cucsFirmwareSystemEntry 2 }

cucsFirmwareSystemRn OBJECT-TYPE
    SYNTAX       SnmpAdminString
    MAX-ACCESS   read-only
    STATUS       current
    DESCRIPTION
        "Cisco UCS firmware:System:rn managed object property"
    ::= { cucsFirmwareSystemEntry 3 }

cucsFirmwareSystemFsmDescr OBJECT-TYPE
    SYNTAX       SnmpAdminString
    MAX-ACCESS   read-only
    STATUS       current
    DESCRIPTION
        "Cisco UCS firmware:System:fsmDescr managed object property"
    ::= { cucsFirmwareSystemEntry 4 }

cucsFirmwareSystemFsmFlags OBJECT-TYPE
    SYNTAX       SnmpAdminString
    MAX-ACCESS   read-only
    STATUS       current
    DESCRIPTION
        "Cisco UCS firmware:System:fsmFlags managed object property"
    ::= { cucsFirmwareSystemEntry 5 }

cucsFirmwareSystemFsmPrev OBJECT-TYPE
    SYNTAX       SnmpAdminString
    MAX-ACCESS   read-only
    STATUS       current
    DESCRIPTION
        "Cisco UCS firmware:System:fsmPrev managed object property"
    ::= { cucsFirmwareSystemEntry 6 }

cucsFirmwareSystemFsmProgr OBJECT-TYPE
    SYNTAX       Gauge32
    MAX-ACCESS   read-only
    STATUS       current
    DESCRIPTION
        "Cisco UCS firmware:System:fsmProgr managed object property"
    ::= { cucsFirmwareSystemEntry 7 }

cucsFirmwareSystemFsmRmtInvErrCode OBJECT-TYPE
    SYNTAX       Gauge32
    MAX-ACCESS   read-only
    STATUS       current
    DESCRIPTION
        "Cisco UCS firmware:System:fsmRmtInvErrCode managed
        object property"
    ::= { cucsFirmwareSystemEntry 8 }

cucsFirmwareSystemFsmRmtInvErrDescr OBJECT-TYPE
    SYNTAX       SnmpAdminString
    MAX-ACCESS   read-only
    STATUS       current
    DESCRIPTION
        "Cisco UCS firmware:System:fsmRmtInvErrDescr managed
        object property"
    ::= { cucsFirmwareSystemEntry 9 }

cucsFirmwareSystemFsmRmtInvRslt OBJECT-TYPE
    SYNTAX       CucsConditionRemoteInvRslt
    MAX-ACCESS   read-only
    STATUS       current
    DESCRIPTION
        "Cisco UCS firmware:System:fsmRmtInvRslt managed object property"
    ::= { cucsFirmwareSystemEntry 10 }

cucsFirmwareSystemFsmStageDescr OBJECT-TYPE
    SYNTAX       SnmpAdminString
    MAX-ACCESS   read-only
    STATUS       current
    DESCRIPTION
        "Cisco UCS firmware:System:fsmStageDescr managed object property"
    ::= { cucsFirmwareSystemEntry 11 }

cucsFirmwareSystemFsmStamp OBJECT-TYPE
    SYNTAX       DateAndTime
    MAX-ACCESS   read-only
    STATUS       current
    DESCRIPTION
        "Cisco UCS firmware:System:fsmStamp managed object property"
    ::= { cucsFirmwareSystemEntry 12 }

cucsFirmwareSystemFsmStatus OBJECT-TYPE
    SYNTAX       SnmpAdminString
    MAX-ACCESS   read-only
    STATUS       current
    DESCRIPTION
        "Cisco UCS firmware:System:fsmStatus managed object property"
    ::= { cucsFirmwareSystemEntry 13 }

cucsFirmwareSystemFsmTry OBJECT-TYPE
    SYNTAX       Gauge32
    MAX-ACCESS   read-only
    STATUS       current
    DESCRIPTION
        "Cisco UCS firmware:System:fsmTry managed object property"
    ::= { cucsFirmwareSystemEntry 14 }

cucsFirmwareSystemOperState OBJECT-TYPE
    SYNTAX       CucsFirmwareInstallState
    MAX-ACCESS   read-only
    STATUS       current
    DESCRIPTION
        "Cisco UCS firmware:System:operState managed object property"
    ::= { cucsFirmwareSystemEntry 15 }

cucsFirmwareSystemState OBJECT-TYPE
    SYNTAX       CucsFirmwareFwState
    MAX-ACCESS   read-only
    STATUS       current
    DESCRIPTION
        "Cisco UCS firmware:System:state managed object property"
    ::= { cucsFirmwareSystemEntry 16 }

cucsFirmwareSystemCompCheckResultTable OBJECT-TYPE
    SYNTAX           SEQUENCE OF CucsFirmwareSystemCompCheckResultEntry
    MAX-ACCESS       not-accessible
    STATUS           current
    DESCRIPTION
        "Cisco UCS firmware:SystemCompCheckResult managed object table"
    ::= { cucsFirmwareObjects 44 }

cucsFirmwareSystemCompCheckResultEntry OBJECT-TYPE
    SYNTAX           CucsFirmwareSystemCompCheckResultEntry
    MAX-ACCESS       not-accessible
    STATUS           current
    DESCRIPTION
        "Entry for the cucsFirmwareSystemCompCheckResultTable table."
    INDEX { cucsFirmwareSystemCompCheckResultInstanceId }
    ::= { cucsFirmwareSystemCompCheckResultTable 1 }

CucsFirmwareSystemCompCheckResultEntry ::= SEQUENCE {
    cucsFirmwareSystemCompCheckResultInstanceId                      CucsManagedObjectId,
    cucsFirmwareSystemCompCheckResultDn                              CucsManagedObjectDn,
    cucsFirmwareSystemCompCheckResultRn                              SnmpAdminString,
    cucsFirmwareSystemCompCheckResultKeyDescr                        SnmpAdminString,
    cucsFirmwareSystemCompCheckResultKeyDn                           SnmpAdminString,
    cucsFirmwareSystemCompCheckResultNonCompDescr                    SnmpAdminString,
    cucsFirmwareSystemCompCheckResultNonCompDns                      SnmpAdminString,
    cucsFirmwareSystemCompCheckResultSubject                         CucsFirmwareEquipmentType
}

cucsFirmwareSystemCompCheckResultInstanceId OBJECT-TYPE
    SYNTAX       CucsManagedObjectId
    MAX-ACCESS   not-accessible
    STATUS       current
    DESCRIPTION
        "Instance identifier of the managed object."
    ::= { cucsFirmwareSystemCompCheckResultEntry 1 }

cucsFirmwareSystemCompCheckResultDn OBJECT-TYPE
    SYNTAX       CucsManagedObjectDn
    MAX-ACCESS   read-only
    STATUS       current
    DESCRIPTION
        "Cisco UCS firmware:SystemCompCheckResult:dn managed
        object property"
    ::= { cucsFirmwareSystemCompCheckResultEntry 2 }

cucsFirmwareSystemCompCheckResultRn OBJECT-TYPE
    SYNTAX       SnmpAdminString
    MAX-ACCESS   read-only
    STATUS       current
    DESCRIPTION
        "Cisco UCS firmware:SystemCompCheckResult:rn managed
        object property"
    ::= { cucsFirmwareSystemCompCheckResultEntry 3 }

cucsFirmwareSystemCompCheckResultKeyDescr OBJECT-TYPE
    SYNTAX       SnmpAdminString
    MAX-ACCESS   read-only
    STATUS       current
    DESCRIPTION
        "Cisco UCS firmware:SystemCompCheckResult:keyDescr
        managed object property"
    ::= { cucsFirmwareSystemCompCheckResultEntry 4 }

cucsFirmwareSystemCompCheckResultKeyDn OBJECT-TYPE
    SYNTAX       SnmpAdminString
    MAX-ACCESS   read-only
    STATUS       current
    DESCRIPTION
        "Cisco UCS firmware:SystemCompCheckResult:keyDn
        managed object property"
    ::= { cucsFirmwareSystemCompCheckResultEntry 5 }

cucsFirmwareSystemCompCheckResultNonCompDescr OBJECT-TYPE
    SYNTAX       SnmpAdminString
    MAX-ACCESS   read-only
    STATUS       current
    DESCRIPTION
        "Cisco UCS firmware:SystemCompCheckResult:nonCompDescr
        managed object property"
    ::= { cucsFirmwareSystemCompCheckResultEntry 6 }

cucsFirmwareSystemCompCheckResultNonCompDns OBJECT-TYPE
    SYNTAX       SnmpAdminString
    MAX-ACCESS   read-only
    STATUS       current
    DESCRIPTION
        "Cisco UCS firmware:SystemCompCheckResult:nonCompDns
        managed object property"
    ::= { cucsFirmwareSystemCompCheckResultEntry 7 }

cucsFirmwareSystemCompCheckResultSubject OBJECT-TYPE
    SYNTAX       CucsFirmwareEquipmentType
    MAX-ACCESS   read-only
    STATUS       current
    DESCRIPTION
        "Cisco UCS firmware:SystemCompCheckResult:subject
        managed object property"
    ::= { cucsFirmwareSystemCompCheckResultEntry 8 }

cucsFirmwareSystemFsmTable OBJECT-TYPE
    SYNTAX           SEQUENCE OF CucsFirmwareSystemFsmEntry
    MAX-ACCESS       not-accessible
    STATUS           current
    DESCRIPTION
        "Cisco UCS firmware:SystemFsm managed object table"
    ::= { cucsFirmwareObjects 45 }

cucsFirmwareSystemFsmEntry OBJECT-TYPE
    SYNTAX           CucsFirmwareSystemFsmEntry
    MAX-ACCESS       not-accessible
    STATUS           current
    DESCRIPTION
        "Entry for the cucsFirmwareSystemFsmTable table."
    INDEX { cucsFirmwareSystemFsmInstanceId }
    ::= { cucsFirmwareSystemFsmTable 1 }

CucsFirmwareSystemFsmEntry ::= SEQUENCE {
    cucsFirmwareSystemFsmInstanceId                                  CucsManagedObjectId,
    cucsFirmwareSystemFsmDn                                          CucsManagedObjectDn,
    cucsFirmwareSystemFsmRn                                          SnmpAdminString,
    cucsFirmwareSystemFsmCompletionTime                              DateAndTime,
    cucsFirmwareSystemFsmCurrentFsm                                  CucsFirmwareSystemFsmCurrentFsm,
    cucsFirmwareSystemFsmDescrData                                   SnmpAdminString,
    cucsFirmwareSystemFsmFsmStatus                                   CucsFsmFsmStageStatus,
    cucsFirmwareSystemFsmProgress                                    Gauge32,
    cucsFirmwareSystemFsmRmtErrCode                                  Gauge32,
    cucsFirmwareSystemFsmRmtErrDescr                                 SnmpAdminString,
    cucsFirmwareSystemFsmRmtRslt                                     CucsConditionRemoteInvRslt
}

cucsFirmwareSystemFsmInstanceId OBJECT-TYPE
    SYNTAX       CucsManagedObjectId
    MAX-ACCESS   not-accessible
    STATUS       current
    DESCRIPTION
        "Instance identifier of the managed object."
    ::= { cucsFirmwareSystemFsmEntry 1 }

cucsFirmwareSystemFsmDn OBJECT-TYPE
    SYNTAX       CucsManagedObjectDn
    MAX-ACCESS   read-only
    STATUS       current
    DESCRIPTION
        "Cisco UCS firmware:SystemFsm:dn managed object property"
    ::= { cucsFirmwareSystemFsmEntry 2 }

cucsFirmwareSystemFsmRn OBJECT-TYPE
    SYNTAX       SnmpAdminString
    MAX-ACCESS   read-only
    STATUS       current
    DESCRIPTION
        "Cisco UCS firmware:SystemFsm:rn managed object property"
    ::= { cucsFirmwareSystemFsmEntry 3 }

cucsFirmwareSystemFsmCompletionTime OBJECT-TYPE
    SYNTAX       DateAndTime
    MAX-ACCESS   read-only
    STATUS       current
    DESCRIPTION
        "Cisco UCS firmware:SystemFsm:completionTime managed
        object property"
    ::= { cucsFirmwareSystemFsmEntry 4 }

cucsFirmwareSystemFsmCurrentFsm OBJECT-TYPE
    SYNTAX       CucsFirmwareSystemFsmCurrentFsm
    MAX-ACCESS   read-only
    STATUS       current
    DESCRIPTION
        "Cisco UCS firmware:SystemFsm:currentFsm managed object property"
    ::= { cucsFirmwareSystemFsmEntry 5 }

cucsFirmwareSystemFsmDescrData OBJECT-TYPE
    SYNTAX       SnmpAdminString
    MAX-ACCESS   read-only
    STATUS       current
    DESCRIPTION
        "Cisco UCS firmware:SystemFsm:descr managed object property"
    ::= { cucsFirmwareSystemFsmEntry 6 }

cucsFirmwareSystemFsmFsmStatus OBJECT-TYPE
    SYNTAX       CucsFsmFsmStageStatus
    MAX-ACCESS   read-only
    STATUS       current
    DESCRIPTION
        "Cisco UCS firmware:SystemFsm:fsmStatus managed object property"
    ::= { cucsFirmwareSystemFsmEntry 7 }

cucsFirmwareSystemFsmProgress OBJECT-TYPE
    SYNTAX       Gauge32
    MAX-ACCESS   read-only
    STATUS       current
    DESCRIPTION
        "Cisco UCS firmware:SystemFsm:progress managed object property"
    ::= { cucsFirmwareSystemFsmEntry 8 }

cucsFirmwareSystemFsmRmtErrCode OBJECT-TYPE
    SYNTAX       Gauge32
    MAX-ACCESS   read-only
    STATUS       current
    DESCRIPTION
        "Cisco UCS firmware:SystemFsm:rmtErrCode managed object property"
    ::= { cucsFirmwareSystemFsmEntry 9 }

cucsFirmwareSystemFsmRmtErrDescr OBJECT-TYPE
    SYNTAX       SnmpAdminString
    MAX-ACCESS   read-only
    STATUS       current
    DESCRIPTION
        "Cisco UCS firmware:SystemFsm:rmtErrDescr managed object property"
    ::= { cucsFirmwareSystemFsmEntry 10 }

cucsFirmwareSystemFsmRmtRslt OBJECT-TYPE
    SYNTAX       CucsConditionRemoteInvRslt
    MAX-ACCESS   read-only
    STATUS       current
    DESCRIPTION
        "Cisco UCS firmware:SystemFsm:rmtRslt managed object property"
    ::= { cucsFirmwareSystemFsmEntry 11 }

cucsFirmwareSystemFsmStageTable OBJECT-TYPE
    SYNTAX           SEQUENCE OF CucsFirmwareSystemFsmStageEntry
    MAX-ACCESS       not-accessible
    STATUS           current
    DESCRIPTION
        "Cisco UCS firmware:SystemFsmStage managed object table"
    ::= { cucsFirmwareObjects 46 }

cucsFirmwareSystemFsmStageEntry OBJECT-TYPE
    SYNTAX           CucsFirmwareSystemFsmStageEntry
    MAX-ACCESS       not-accessible
    STATUS           current
    DESCRIPTION
        "Entry for the cucsFirmwareSystemFsmStageTable table."
    INDEX { cucsFirmwareSystemFsmStageInstanceId }
    ::= { cucsFirmwareSystemFsmStageTable 1 }

CucsFirmwareSystemFsmStageEntry ::= SEQUENCE {
    cucsFirmwareSystemFsmStageInstanceId                             CucsManagedObjectId,
    cucsFirmwareSystemFsmStageDn                                     CucsManagedObjectDn,
    cucsFirmwareSystemFsmStageRn                                     SnmpAdminString,
    cucsFirmwareSystemFsmStageDescrData                              SnmpAdminString,
    cucsFirmwareSystemFsmStageLastUpdateTime                         DateAndTime,
    cucsFirmwareSystemFsmStageName                                   CucsFirmwareSystemFsmStageName,
    cucsFirmwareSystemFsmStageOrder                                  Gauge32,
    cucsFirmwareSystemFsmStageRetry                                  Gauge32,
    cucsFirmwareSystemFsmStageStageStatus                            CucsFsmFsmStageStatus
}

cucsFirmwareSystemFsmStageInstanceId OBJECT-TYPE
    SYNTAX       CucsManagedObjectId
    MAX-ACCESS   not-accessible
    STATUS       current
    DESCRIPTION
        "Instance identifier of the managed object."
    ::= { cucsFirmwareSystemFsmStageEntry 1 }

cucsFirmwareSystemFsmStageDn OBJECT-TYPE
    SYNTAX       CucsManagedObjectDn
    MAX-ACCESS   read-only
    STATUS       current
    DESCRIPTION
        "Cisco UCS firmware:SystemFsmStage:dn managed object property"
    ::= { cucsFirmwareSystemFsmStageEntry 2 }

cucsFirmwareSystemFsmStageRn OBJECT-TYPE
    SYNTAX       SnmpAdminString
    MAX-ACCESS   read-only
    STATUS       current
    DESCRIPTION
        "Cisco UCS firmware:SystemFsmStage:rn managed object property"
    ::= { cucsFirmwareSystemFsmStageEntry 3 }

cucsFirmwareSystemFsmStageDescrData OBJECT-TYPE
    SYNTAX       SnmpAdminString
    MAX-ACCESS   read-only
    STATUS       current
    DESCRIPTION
        "Cisco UCS firmware:SystemFsmStage:descr managed object property"
    ::= { cucsFirmwareSystemFsmStageEntry 4 }

cucsFirmwareSystemFsmStageLastUpdateTime OBJECT-TYPE
    SYNTAX       DateAndTime
    MAX-ACCESS   read-only
    STATUS       current
    DESCRIPTION
        "Cisco UCS firmware:SystemFsmStage:lastUpdateTime
        managed object property"
    ::= { cucsFirmwareSystemFsmStageEntry 5 }

cucsFirmwareSystemFsmStageName OBJECT-TYPE
    SYNTAX       CucsFirmwareSystemFsmStageName
    MAX-ACCESS   read-only
    STATUS       current
    DESCRIPTION
        "Cisco UCS firmware:SystemFsmStage:name managed object property"
    ::= { cucsFirmwareSystemFsmStageEntry 6 }

cucsFirmwareSystemFsmStageOrder OBJECT-TYPE
    SYNTAX       Gauge32
    MAX-ACCESS   read-only
    STATUS       current
    DESCRIPTION
        "Cisco UCS firmware:SystemFsmStage:order managed object property"
    ::= { cucsFirmwareSystemFsmStageEntry 7 }

cucsFirmwareSystemFsmStageRetry OBJECT-TYPE
    SYNTAX       Gauge32
    MAX-ACCESS   read-only
    STATUS       current
    DESCRIPTION
        "Cisco UCS firmware:SystemFsmStage:retry managed object property"
    ::= { cucsFirmwareSystemFsmStageEntry 8 }

cucsFirmwareSystemFsmStageStageStatus OBJECT-TYPE
    SYNTAX       CucsFsmFsmStageStatus
    MAX-ACCESS   read-only
    STATUS       current
    DESCRIPTION
        "Cisco UCS firmware:SystemFsmStage:stageStatus
        managed object property"
    ::= { cucsFirmwareSystemFsmStageEntry 9 }

cucsFirmwareSystemFsmTaskTable OBJECT-TYPE
    SYNTAX           SEQUENCE OF CucsFirmwareSystemFsmTaskEntry
    MAX-ACCESS       not-accessible
    STATUS           current
    DESCRIPTION
        "Cisco UCS firmware:SystemFsmTask managed object table"
    ::= { cucsFirmwareObjects 47 }

cucsFirmwareSystemFsmTaskEntry OBJECT-TYPE
    SYNTAX           CucsFirmwareSystemFsmTaskEntry
    MAX-ACCESS       not-accessible
    STATUS           current
    DESCRIPTION
        "Entry for the cucsFirmwareSystemFsmTaskTable table."
    INDEX { cucsFirmwareSystemFsmTaskInstanceId }
    ::= { cucsFirmwareSystemFsmTaskTable 1 }

CucsFirmwareSystemFsmTaskEntry ::= SEQUENCE {
    cucsFirmwareSystemFsmTaskInstanceId                              CucsManagedObjectId,
    cucsFirmwareSystemFsmTaskDn                                      CucsManagedObjectDn,
    cucsFirmwareSystemFsmTaskRn                                      SnmpAdminString,
    cucsFirmwareSystemFsmTaskCompletion                              CucsFsmCompletion,
    cucsFirmwareSystemFsmTaskFlags                                   CucsFirmwareSystemFsmTaskFlags,
    cucsFirmwareSystemFsmTaskItem                                    CucsFirmwareSystemFsmTaskItem,
    cucsFirmwareSystemFsmTaskSeqId                                   Gauge32
}

cucsFirmwareSystemFsmTaskInstanceId OBJECT-TYPE
    SYNTAX       CucsManagedObjectId
    MAX-ACCESS   not-accessible
    STATUS       current
    DESCRIPTION
        "Instance identifier of the managed object."
    ::= { cucsFirmwareSystemFsmTaskEntry 1 }

cucsFirmwareSystemFsmTaskDn OBJECT-TYPE
    SYNTAX       CucsManagedObjectDn
    MAX-ACCESS   read-only
    STATUS       current
    DESCRIPTION
        "Cisco UCS firmware:SystemFsmTask:dn managed object property"
    ::= { cucsFirmwareSystemFsmTaskEntry 2 }

cucsFirmwareSystemFsmTaskRn OBJECT-TYPE
    SYNTAX       SnmpAdminString
    MAX-ACCESS   read-only
    STATUS       current
    DESCRIPTION
        "Cisco UCS firmware:SystemFsmTask:rn managed object property"
    ::= { cucsFirmwareSystemFsmTaskEntry 3 }

cucsFirmwareSystemFsmTaskCompletion OBJECT-TYPE
    SYNTAX       CucsFsmCompletion
    MAX-ACCESS   read-only
    STATUS       current
    DESCRIPTION
        "Cisco UCS firmware:SystemFsmTask:completion managed
        object property"
    ::= { cucsFirmwareSystemFsmTaskEntry 4 }

cucsFirmwareSystemFsmTaskFlags OBJECT-TYPE
    SYNTAX       CucsFirmwareSystemFsmTaskFlags
    MAX-ACCESS   read-only
    STATUS       current
    DESCRIPTION
        "Cisco UCS firmware:SystemFsmTask:flags managed object property"
    ::= { cucsFirmwareSystemFsmTaskEntry 5 }

cucsFirmwareSystemFsmTaskItem OBJECT-TYPE
    SYNTAX       CucsFirmwareSystemFsmTaskItem
    MAX-ACCESS   read-only
    STATUS       current
    DESCRIPTION
        "Cisco UCS firmware:SystemFsmTask:item managed object property"
    ::= { cucsFirmwareSystemFsmTaskEntry 6 }

cucsFirmwareSystemFsmTaskSeqId OBJECT-TYPE
    SYNTAX       Gauge32
    MAX-ACCESS   read-only
    STATUS       current
    DESCRIPTION
        "Cisco UCS firmware:SystemFsmTask:seqId managed object property"
    ::= { cucsFirmwareSystemFsmTaskEntry 7 }

cucsFirmwareTypeTable OBJECT-TYPE
    SYNTAX           SEQUENCE OF CucsFirmwareTypeEntry
    MAX-ACCESS       not-accessible
    STATUS           current
    DESCRIPTION
        "Cisco UCS firmware:Type managed object table"
    ::= { cucsFirmwareObjects 19 }

cucsFirmwareTypeEntry OBJECT-TYPE
    SYNTAX           CucsFirmwareTypeEntry
    MAX-ACCESS       not-accessible
    STATUS           current
    DESCRIPTION
        "Entry for the cucsFirmwareTypeTable table."
    INDEX { cucsFirmwareTypeInstanceId }
    ::= { cucsFirmwareTypeTable 1 }

CucsFirmwareTypeEntry ::= SEQUENCE {
    cucsFirmwareTypeInstanceId                                       CucsManagedObjectId,
    cucsFirmwareTypeDn                                               CucsManagedObjectDn,
    cucsFirmwareTypeRn                                               SnmpAdminString,
    cucsFirmwareTypeEp                                               CucsFirmwareType,
    cucsFirmwareTypeInvTag                                           SnmpAdminString,
    cucsFirmwareTypeMaxVer                                           SnmpAdminString,
    cucsFirmwareTypeMinVer                                           SnmpAdminString
}

cucsFirmwareTypeInstanceId OBJECT-TYPE
    SYNTAX       CucsManagedObjectId
    MAX-ACCESS   not-accessible
    STATUS       current
    DESCRIPTION
        "Instance identifier of the managed object."
    ::= { cucsFirmwareTypeEntry 1 }

cucsFirmwareTypeDn OBJECT-TYPE
    SYNTAX       CucsManagedObjectDn
    MAX-ACCESS   read-only
    STATUS       current
    DESCRIPTION
        "Cisco UCS firmware:Type:dn managed object property"
    ::= { cucsFirmwareTypeEntry 2 }

cucsFirmwareTypeRn OBJECT-TYPE
    SYNTAX       SnmpAdminString
    MAX-ACCESS   read-only
    STATUS       current
    DESCRIPTION
        "Cisco UCS firmware:Type:rn managed object property"
    ::= { cucsFirmwareTypeEntry 3 }

cucsFirmwareTypeEp OBJECT-TYPE
    SYNTAX       CucsFirmwareType
    MAX-ACCESS   read-only
    STATUS       current
    DESCRIPTION
        "Cisco UCS firmware:Type:ep managed object property"
    ::= { cucsFirmwareTypeEntry 4 }

cucsFirmwareTypeInvTag OBJECT-TYPE
    SYNTAX       SnmpAdminString
    MAX-ACCESS   read-only
    STATUS       current
    DESCRIPTION
        "Cisco UCS firmware:Type:invTag managed object property"
    ::= { cucsFirmwareTypeEntry 5 }

cucsFirmwareTypeMaxVer OBJECT-TYPE
    SYNTAX       SnmpAdminString
    MAX-ACCESS   read-only
    STATUS       current
    DESCRIPTION
        "Cisco UCS firmware:Type:maxVer managed object property"
    ::= { cucsFirmwareTypeEntry 6 }

cucsFirmwareTypeMinVer OBJECT-TYPE
    SYNTAX       SnmpAdminString
    MAX-ACCESS   read-only
    STATUS       current
    DESCRIPTION
        "Cisco UCS firmware:Type:minVer managed object property"
    ::= { cucsFirmwareTypeEntry 7 }

cucsFirmwareUcscInfoTable OBJECT-TYPE
    SYNTAX           SEQUENCE OF CucsFirmwareUcscInfoEntry
    MAX-ACCESS       not-accessible
    STATUS           current
    DESCRIPTION
        "Cisco UCS firmware:UcscInfo managed object table"
    ::= { cucsFirmwareObjects 52 }

cucsFirmwareUcscInfoEntry OBJECT-TYPE
    SYNTAX           CucsFirmwareUcscInfoEntry
    MAX-ACCESS       not-accessible
    STATUS           current
    DESCRIPTION
        "Entry for the cucsFirmwareUcscInfoTable table."
    INDEX { cucsFirmwareUcscInfoInstanceId }
    ::= { cucsFirmwareUcscInfoTable 1 }

CucsFirmwareUcscInfoEntry ::= SEQUENCE {
    cucsFirmwareUcscInfoInstanceId                                   CucsManagedObjectId,
    cucsFirmwareUcscInfoDn                                           CucsManagedObjectDn,
    cucsFirmwareUcscInfoRn                                           SnmpAdminString,
    cucsFirmwareUcscInfoConnProtocol                                 CucsExtpolConnProtocol,
    cucsFirmwareUcscInfoHost                                         SnmpAdminString,
    cucsFirmwareUcscInfoVersion                                      SnmpAdminString
}

cucsFirmwareUcscInfoInstanceId OBJECT-TYPE
    SYNTAX       CucsManagedObjectId
    MAX-ACCESS   not-accessible
    STATUS       current
    DESCRIPTION
        "Instance identifier of the managed object."
    ::= { cucsFirmwareUcscInfoEntry 1 }

cucsFirmwareUcscInfoDn OBJECT-TYPE
    SYNTAX       CucsManagedObjectDn
    MAX-ACCESS   read-only
    STATUS       current
    DESCRIPTION
        "Cisco UCS firmware:UcscInfo:dn managed object property"
    ::= { cucsFirmwareUcscInfoEntry 2 }

cucsFirmwareUcscInfoRn OBJECT-TYPE
    SYNTAX       SnmpAdminString
    MAX-ACCESS   read-only
    STATUS       current
    DESCRIPTION
        "Cisco UCS firmware:UcscInfo:rn managed object property"
    ::= { cucsFirmwareUcscInfoEntry 3 }

cucsFirmwareUcscInfoConnProtocol OBJECT-TYPE
    SYNTAX       CucsExtpolConnProtocol
    MAX-ACCESS   read-only
    STATUS       current
    DESCRIPTION
        "Cisco UCS firmware:UcscInfo:connProtocol managed object property"
    ::= { cucsFirmwareUcscInfoEntry 4 }

cucsFirmwareUcscInfoHost OBJECT-TYPE
    SYNTAX       SnmpAdminString
    MAX-ACCESS   read-only
    STATUS       current
    DESCRIPTION
        "Cisco UCS firmware:UcscInfo:host managed object property"
    ::= { cucsFirmwareUcscInfoEntry 5 }

cucsFirmwareUcscInfoVersion OBJECT-TYPE
    SYNTAX       SnmpAdminString
    MAX-ACCESS   read-only
    STATUS       current
    DESCRIPTION
        "Cisco UCS firmware:UcscInfo:version managed object property"
    ::= { cucsFirmwareUcscInfoEntry 6 }

cucsFirmwareUpdatableTable OBJECT-TYPE
    SYNTAX           SEQUENCE OF CucsFirmwareUpdatableEntry
    MAX-ACCESS       not-accessible
    STATUS           current
    DESCRIPTION
        "Cisco UCS firmware:Updatable managed object table"
    ::= { cucsFirmwareObjects 20 }

cucsFirmwareUpdatableEntry OBJECT-TYPE
    SYNTAX           CucsFirmwareUpdatableEntry
    MAX-ACCESS       not-accessible
    STATUS           current
    DESCRIPTION
        "Entry for the cucsFirmwareUpdatableTable table."
    INDEX { cucsFirmwareUpdatableInstanceId }
    ::= { cucsFirmwareUpdatableTable 1 }

CucsFirmwareUpdatableEntry ::= SEQUENCE {
    cucsFirmwareUpdatableInstanceId                                  CucsManagedObjectId,
    cucsFirmwareUpdatableDn                                          CucsManagedObjectDn,
    cucsFirmwareUpdatableRn                                          SnmpAdminString,
    cucsFirmwareUpdatableAdminState                                  CucsFirmwareTriggerState,
    cucsFirmwareUpdatableDeployment                                  CucsFirmwareUpdatableDeployment,
    cucsFirmwareUpdatableOperState                                   CucsFirmwareImageState,
    cucsFirmwareUpdatableOperStateQual                               CucsFirmwareImageError,
    cucsFirmwareUpdatablePrevVersion                                 SnmpAdminString,
    cucsFirmwareUpdatableVersion                                     SnmpAdminString
}

cucsFirmwareUpdatableInstanceId OBJECT-TYPE
    SYNTAX       CucsManagedObjectId
    MAX-ACCESS   not-accessible
    STATUS       current
    DESCRIPTION
        "Instance identifier of the managed object."
    ::= { cucsFirmwareUpdatableEntry 1 }

cucsFirmwareUpdatableDn OBJECT-TYPE
    SYNTAX       CucsManagedObjectDn
    MAX-ACCESS   read-only
    STATUS       current
    DESCRIPTION
        "Cisco UCS firmware:Updatable:dn managed object property"
    ::= { cucsFirmwareUpdatableEntry 2 }

cucsFirmwareUpdatableRn OBJECT-TYPE
    SYNTAX       SnmpAdminString
    MAX-ACCESS   read-only
    STATUS       current
    DESCRIPTION
        "Cisco UCS firmware:Updatable:rn managed object property"
    ::= { cucsFirmwareUpdatableEntry 3 }

cucsFirmwareUpdatableAdminState OBJECT-TYPE
    SYNTAX       CucsFirmwareTriggerState
    MAX-ACCESS   read-only
    STATUS       current
    DESCRIPTION
        "Cisco UCS firmware:Updatable:adminState managed object property"
    ::= { cucsFirmwareUpdatableEntry 4 }

cucsFirmwareUpdatableDeployment OBJECT-TYPE
    SYNTAX       CucsFirmwareUpdatableDeployment
    MAX-ACCESS   read-only
    STATUS       current
    DESCRIPTION
        "Cisco UCS firmware:Updatable:deployment managed object property"
    ::= { cucsFirmwareUpdatableEntry 5 }

cucsFirmwareUpdatableOperState OBJECT-TYPE
    SYNTAX       CucsFirmwareImageState
    MAX-ACCESS   read-only
    STATUS       current
    DESCRIPTION
        "Cisco UCS firmware:Updatable:operState managed object property"
    ::= { cucsFirmwareUpdatableEntry 6 }

cucsFirmwareUpdatableOperStateQual OBJECT-TYPE
    SYNTAX       CucsFirmwareImageError
    MAX-ACCESS   read-only
    STATUS       current
    DESCRIPTION
        "Cisco UCS firmware:Updatable:operStateQual managed
        object property"
    ::= { cucsFirmwareUpdatableEntry 7 }

cucsFirmwareUpdatablePrevVersion OBJECT-TYPE
    SYNTAX       SnmpAdminString
    MAX-ACCESS   read-only
    STATUS       current
    DESCRIPTION
        "Cisco UCS firmware:Updatable:prevVersion managed object property"
    ::= { cucsFirmwareUpdatableEntry 8 }

cucsFirmwareUpdatableVersion OBJECT-TYPE
    SYNTAX       SnmpAdminString
    MAX-ACCESS   read-only
    STATUS       current
    DESCRIPTION
        "Cisco UCS firmware:Updatable:version managed object property"
    ::= { cucsFirmwareUpdatableEntry 9 }

cucsFirmwareUpgradeConstraintTable OBJECT-TYPE
    SYNTAX           SEQUENCE OF CucsFirmwareUpgradeConstraintEntry
    MAX-ACCESS       not-accessible
    STATUS           current
    DESCRIPTION
        "Cisco UCS firmware:UpgradeConstraint managed object table"
    ::= { cucsFirmwareObjects 24 }

cucsFirmwareUpgradeConstraintEntry OBJECT-TYPE
    SYNTAX           CucsFirmwareUpgradeConstraintEntry
    MAX-ACCESS       not-accessible
    STATUS           current
    DESCRIPTION
        "Entry for the cucsFirmwareUpgradeConstraintTable table."
    INDEX { cucsFirmwareUpgradeConstraintInstanceId }
    ::= { cucsFirmwareUpgradeConstraintTable 1 }

CucsFirmwareUpgradeConstraintEntry ::= SEQUENCE {
    cucsFirmwareUpgradeConstraintInstanceId                          CucsManagedObjectId,
    cucsFirmwareUpgradeConstraintDn                                  CucsManagedObjectDn,
    cucsFirmwareUpgradeConstraintRn                                  SnmpAdminString,
    cucsFirmwareUpgradeConstraintMinVer                              SnmpAdminString
}

cucsFirmwareUpgradeConstraintInstanceId OBJECT-TYPE
    SYNTAX       CucsManagedObjectId
    MAX-ACCESS   not-accessible
    STATUS       current
    DESCRIPTION
        "Instance identifier of the managed object."
    ::= { cucsFirmwareUpgradeConstraintEntry 1 }

cucsFirmwareUpgradeConstraintDn OBJECT-TYPE
    SYNTAX       CucsManagedObjectDn
    MAX-ACCESS   read-only
    STATUS       current
    DESCRIPTION
        "Cisco UCS firmware:UpgradeConstraint:dn managed object property"
    ::= { cucsFirmwareUpgradeConstraintEntry 2 }

cucsFirmwareUpgradeConstraintRn OBJECT-TYPE
    SYNTAX       SnmpAdminString
    MAX-ACCESS   read-only
    STATUS       current
    DESCRIPTION
        "Cisco UCS firmware:UpgradeConstraint:rn managed object property"
    ::= { cucsFirmwareUpgradeConstraintEntry 3 }

cucsFirmwareUpgradeConstraintMinVer OBJECT-TYPE
    SYNTAX       SnmpAdminString
    MAX-ACCESS   read-only
    STATUS       current
    DESCRIPTION
        "Cisco UCS firmware:UpgradeConstraint:minVer managed
        object property"
    ::= { cucsFirmwareUpgradeConstraintEntry 4 }

cucsFirmwareUpgradeDetailTable OBJECT-TYPE
    SYNTAX           SEQUENCE OF CucsFirmwareUpgradeDetailEntry
    MAX-ACCESS       not-accessible
    STATUS           current
    DESCRIPTION
        "Cisco UCS firmware:UpgradeDetail managed object table"
    ::= { cucsFirmwareObjects 48 }

cucsFirmwareUpgradeDetailEntry OBJECT-TYPE
    SYNTAX           CucsFirmwareUpgradeDetailEntry
    MAX-ACCESS       not-accessible
    STATUS           current
    DESCRIPTION
        "Entry for the cucsFirmwareUpgradeDetailTable table."
    INDEX { cucsFirmwareUpgradeDetailInstanceId }
    ::= { cucsFirmwareUpgradeDetailTable 1 }

CucsFirmwareUpgradeDetailEntry ::= SEQUENCE {
    cucsFirmwareUpgradeDetailInstanceId                              CucsManagedObjectId,
    cucsFirmwareUpgradeDetailDn                                      CucsManagedObjectDn,
    cucsFirmwareUpgradeDetailRn                                      SnmpAdminString,
    cucsFirmwareUpgradeDetailCategory                                CucsFirmwareUpgradeCategory,
    cucsFirmwareUpgradeDetailDescription                             SnmpAdminString,
    cucsFirmwareUpgradeDetailId                                      Gauge32,
    cucsFirmwareUpgradeDetailSeverity                                CucsFirmwareUpgradeSeverity
}

cucsFirmwareUpgradeDetailInstanceId OBJECT-TYPE
    SYNTAX       CucsManagedObjectId
    MAX-ACCESS   not-accessible
    STATUS       current
    DESCRIPTION
        "Instance identifier of the managed object."
    ::= { cucsFirmwareUpgradeDetailEntry 1 }

cucsFirmwareUpgradeDetailDn OBJECT-TYPE
    SYNTAX       CucsManagedObjectDn
    MAX-ACCESS   read-only
    STATUS       current
    DESCRIPTION
        "Cisco UCS firmware:UpgradeDetail:dn managed object property"
    ::= { cucsFirmwareUpgradeDetailEntry 2 }

cucsFirmwareUpgradeDetailRn OBJECT-TYPE
    SYNTAX       SnmpAdminString
    MAX-ACCESS   read-only
    STATUS       current
    DESCRIPTION
        "Cisco UCS firmware:UpgradeDetail:rn managed object property"
    ::= { cucsFirmwareUpgradeDetailEntry 3 }

cucsFirmwareUpgradeDetailCategory OBJECT-TYPE
    SYNTAX       CucsFirmwareUpgradeCategory
    MAX-ACCESS   read-only
    STATUS       current
    DESCRIPTION
        "Cisco UCS firmware:UpgradeDetail:category managed
        object property"
    ::= { cucsFirmwareUpgradeDetailEntry 4 }

cucsFirmwareUpgradeDetailDescription OBJECT-TYPE
    SYNTAX       SnmpAdminString
    MAX-ACCESS   read-only
    STATUS       current
    DESCRIPTION
        "Cisco UCS firmware:UpgradeDetail:description managed
        object property"
    ::= { cucsFirmwareUpgradeDetailEntry 5 }

cucsFirmwareUpgradeDetailId OBJECT-TYPE
    SYNTAX       Gauge32
    MAX-ACCESS   read-only
    STATUS       current
    DESCRIPTION
        "Cisco UCS firmware:UpgradeDetail:id managed object property"
    ::= { cucsFirmwareUpgradeDetailEntry 6 }

cucsFirmwareUpgradeDetailSeverity OBJECT-TYPE
    SYNTAX       CucsFirmwareUpgradeSeverity
    MAX-ACCESS   read-only
    STATUS       current
    DESCRIPTION
        "Cisco UCS firmware:UpgradeDetail:severity managed
        object property"
    ::= { cucsFirmwareUpgradeDetailEntry 7 }

cucsFirmwareUpgradeInfoTable OBJECT-TYPE
    SYNTAX           SEQUENCE OF CucsFirmwareUpgradeInfoEntry
    MAX-ACCESS       not-accessible
    STATUS           current
    DESCRIPTION
        "Cisco UCS firmware:UpgradeInfo managed object table"
    ::= { cucsFirmwareObjects 49 }

cucsFirmwareUpgradeInfoEntry OBJECT-TYPE
    SYNTAX           CucsFirmwareUpgradeInfoEntry
    MAX-ACCESS       not-accessible
    STATUS           current
    DESCRIPTION
        "Entry for the cucsFirmwareUpgradeInfoTable table."
    INDEX { cucsFirmwareUpgradeInfoInstanceId }
    ::= { cucsFirmwareUpgradeInfoTable 1 }

CucsFirmwareUpgradeInfoEntry ::= SEQUENCE {
    cucsFirmwareUpgradeInfoInstanceId                                CucsManagedObjectId,
    cucsFirmwareUpgradeInfoDn                                        CucsManagedObjectDn,
    cucsFirmwareUpgradeInfoRn                                        SnmpAdminString,
    cucsFirmwareUpgradeInfoMessage                                   SnmpAdminString,
    cucsFirmwareUpgradeInfoTimeStamp                                 DateAndTime,
    cucsFirmwareUpgradeInfoValidateStatus                            CucsFirmwareUpgradeStatus,
    cucsFirmwareUpgradeInfoVersion                                   SnmpAdminString
}

cucsFirmwareUpgradeInfoInstanceId OBJECT-TYPE
    SYNTAX       CucsManagedObjectId
    MAX-ACCESS   not-accessible
    STATUS       current
    DESCRIPTION
        "Instance identifier of the managed object."
    ::= { cucsFirmwareUpgradeInfoEntry 1 }

cucsFirmwareUpgradeInfoDn OBJECT-TYPE
    SYNTAX       CucsManagedObjectDn
    MAX-ACCESS   read-only
    STATUS       current
    DESCRIPTION
        "Cisco UCS firmware:UpgradeInfo:dn managed object property"
    ::= { cucsFirmwareUpgradeInfoEntry 2 }

cucsFirmwareUpgradeInfoRn OBJECT-TYPE
    SYNTAX       SnmpAdminString
    MAX-ACCESS   read-only
    STATUS       current
    DESCRIPTION
        "Cisco UCS firmware:UpgradeInfo:rn managed object property"
    ::= { cucsFirmwareUpgradeInfoEntry 3 }

cucsFirmwareUpgradeInfoMessage OBJECT-TYPE
    SYNTAX       SnmpAdminString
    MAX-ACCESS   read-only
    STATUS       current
    DESCRIPTION
        "Cisco UCS firmware:UpgradeInfo:message managed object property"
    ::= { cucsFirmwareUpgradeInfoEntry 4 }

cucsFirmwareUpgradeInfoTimeStamp OBJECT-TYPE
    SYNTAX       DateAndTime
    MAX-ACCESS   read-only
    STATUS       current
    DESCRIPTION
        "Cisco UCS firmware:UpgradeInfo:timeStamp managed object property"
    ::= { cucsFirmwareUpgradeInfoEntry 5 }

cucsFirmwareUpgradeInfoValidateStatus OBJECT-TYPE
    SYNTAX       CucsFirmwareUpgradeStatus
    MAX-ACCESS   read-only
    STATUS       current
    DESCRIPTION
        "Cisco UCS firmware:UpgradeInfo:validateStatus
        managed object property"
    ::= { cucsFirmwareUpgradeInfoEntry 6 }

cucsFirmwareUpgradeInfoVersion OBJECT-TYPE
    SYNTAX       SnmpAdminString
    MAX-ACCESS   read-only
    STATUS       current
    DESCRIPTION
        "Cisco UCS firmware:UpgradeInfo:version managed object property"
    ::= { cucsFirmwareUpgradeInfoEntry 7 }

END
